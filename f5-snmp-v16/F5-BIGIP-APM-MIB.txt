F5-BIGIP-APM-MIB DEFINITIONS ::= BEGIN
--================================================================
-- F5-BIGIP-APM-MIB 
--     A private enterprise MIB for F5  traffic management 
--     systems.
--     VERSION: 16.0.1.1
--================================================================

IMPORTS
    OBJECT-TYPE, NOTIFICATION-TYPE, MODULE-IDENTITY,
    Opaque, enterprises, Counter32, Counter64, TimeTicks
        FROM SNMPv2-SMI

    Gauge 
        FROM RFC1155-SMI 

    TEXTUAL-CONVENTION, MacAddress 
        FROM SNMPv2-TC 

    OBJECT-GROUP, MODULE-COMPLIANCE
        FROM SNMPv2-CONF

    InetAddress, InetAddressType, InetPortNumber
      FROM INET-ADDRESS-MIB

    bigipTrafficMgmt, bigipCompliances, bigipGroups, LongDisplayString
      FROM F5-BIGIP-COMMON-MIB;

--================================================================
bigipApm MODULE-IDENTITY
    LAST-UPDATED "202004092221Z" -- Thu Apr  9 22:21:57 UTC 2020 
    ORGANIZATION "F5 Networks, Inc."
    CONTACT-INFO
         "postal: F5 Networks, Inc. 
	 	  801 Fifth Avenue
                  Seattle, WA 98104
          phone:  (206) 272-6500
          email:  support@f5.com"

    DESCRIPTION
        "Top-level infrastructure of the F5 enterprise MIB tree." 
    ::= { bigipTrafficMgmt 6 }

--================================================================

--bigipApm
apmProfiles                    OBJECT IDENTIFIER ::= { bigipApm 1 }
apmProfileAccessStat           OBJECT IDENTIFIER ::= { apmProfiles 1 }
apmProfileConnectivityStat     OBJECT IDENTIFIER ::= { apmProfiles 2 }
apmProfileRewriteStat          OBJECT IDENTIFIER ::= { apmProfiles 3 }
apmAccessStat                  OBJECT IDENTIFIER ::= { apmProfiles 4 }
apmGlobalConnectivityStat      OBJECT IDENTIFIER ::= { apmProfiles 5 }
apmGlobalRewriteStat           OBJECT IDENTIFIER ::= { apmProfiles 6 }
apmProfileAccessAgentStat      OBJECT IDENTIFIER ::= { apmProfiles 7 }
apmProfileAccessMiscStat       OBJECT IDENTIFIER ::= { apmProfiles 8 }
apmLeasepool                   OBJECT IDENTIFIER ::= { bigipApm 2 }
apmLeasepoolStat               OBJECT IDENTIFIER ::= { apmLeasepool 1 }
apmAcl                         OBJECT IDENTIFIER ::= { bigipApm 3 }
apmAclStat                     OBJECT IDENTIFIER ::= { apmAcl 1 }
apmGlobalLicenseStat           OBJECT IDENTIFIER ::= { apmProfiles 9 }
apmIpv6Leasepool               OBJECT IDENTIFIER ::= { bigipApm 4 }
apmIpv6LeasepoolStat           OBJECT IDENTIFIER ::= { apmIpv6Leasepool 1 }


--==================================================================
-- Profile_access_stat
--==================================================================
apmPaStatResetStats OBJECT-TYPE 
	SYNTAX INTEGER
	MAX-ACCESS read-write
	STATUS current
	DESCRIPTION
		"The action to reset resettable statistics data in apmProfileAccessStat.
		 Setting this value to 1 will reset statistics data.
		 Note, some statistics data may not be reset including data that are incremental counters."
	::= { apmProfileAccessStat 1 } 

apmPaStatNumber OBJECT-TYPE 
	SYNTAX INTEGER
	MAX-ACCESS read-only
	STATUS current
	DESCRIPTION
		"The number of apmProfileAccessStat entries in the table."
	::= { apmProfileAccessStat 2 } 

apmPaStatTable OBJECT-TYPE
	SYNTAX SEQUENCE OF ApmPaStatEntry
	MAX-ACCESS not-accessible
	STATUS current
	DESCRIPTION
		"A table containing statistic information of access profiles."
	::= { apmProfileAccessStat 3 } 

apmPaStatEntry OBJECT-TYPE
	SYNTAX  ApmPaStatEntry
	MAX-ACCESS not-accessible
	STATUS current
	DESCRIPTION
		"Columns in the apmPaStat Table"
	INDEX {
		apmPaStatName,
		apmPaStatVsName
	}
	::= { apmPaStatTable 1 } 

ApmPaStatEntry ::= 
	SEQUENCE {
        	apmPaStatName                                             LongDisplayString,
        	apmPaStatConfigSyncState                                  Counter64,
        	apmPaStatTotalSessions                                    Counter64,
        	apmPaStatTotalEstablishedStateSessions                    Counter64,
        	apmPaStatCurrentActiveSessions                            Counter64,
        	apmPaStatCurrentPendingSessions                           Counter64,
        	apmPaStatCurrentCompletedSessions                         Counter64,
        	apmPaStatUserLoggedoutSessions                            Counter64,
        	apmPaStatAdminTerminatedSessions                          Counter64,
        	apmPaStatMiscTerminatedSessions                           Counter64,
        	apmPaStatAccessPolicyResultAllow                          Counter64,
        	apmPaStatAccessPolicyResultDeny                           Counter64,
        	apmPaStatAccessPolicyResultRedirect                       Counter64,
        	apmPaStatAccessPolicyResultRedirectWithSession            Counter64,
        	apmPaStatEndingDenyAgentTotalInstances                    Counter64,
        	apmPaStatEndingDenyAgentTotalUsages                       Counter64,
        	apmPaStatEndingDenyAgentTotalSuccesses                    Counter64,
        	apmPaStatEndingDenyAgentTotalFailures                     Counter64,
        	apmPaStatEndingDenyAgentTotalErrors                       Counter64,
        	apmPaStatEndingDenyAgentTotalSessVars                     Counter64,
        	apmPaStatEndingRedirectAgentTotalInstances                Counter64,
        	apmPaStatEndingRedirectAgentTotalUsages                   Counter64,
        	apmPaStatEndingRedirectAgentTotalSuccesses                Counter64,
        	apmPaStatEndingRedirectAgentTotalFailures                 Counter64,
        	apmPaStatEndingRedirectAgentTotalErrors                   Counter64,
        	apmPaStatEndingRedirectAgentTotalSessVars                 Counter64,
        	apmPaStatEndingAllowAgentTotalInstances                   Counter64,
        	apmPaStatEndingAllowAgentTotalUsages                      Counter64,
        	apmPaStatEndingAllowAgentTotalSuccesses                   Counter64,
        	apmPaStatEndingAllowAgentTotalFailures                    Counter64,
        	apmPaStatEndingAllowAgentTotalErrors                      Counter64,
        	apmPaStatEndingAllowAgentTotalSessVars                    Counter64,
        	apmPaStatAdAgentTotalInstances                            Counter64,
        	apmPaStatAdAgentTotalUsages                               Counter64,
        	apmPaStatAdAgentTotalSuccesses                            Counter64,
        	apmPaStatAdAgentTotalFailures                             Counter64,
        	apmPaStatAdAgentTotalErrors                               Counter64,
        	apmPaStatAdAgentTotalSessVars                             Counter64,
        	apmPaStatClientCertAgentTotalInstances                    Counter64,
        	apmPaStatClientCertAgentTotalUsages                       Counter64,
        	apmPaStatClientCertAgentTotalSuccesses                    Counter64,
        	apmPaStatClientCertAgentTotalFailures                     Counter64,
        	apmPaStatClientCertAgentTotalErrors                       Counter64,
        	apmPaStatClientCertAgentTotalSessVars                     Counter64,
        	apmPaStatHttpAgentTotalInstances                          Counter64,
        	apmPaStatHttpAgentTotalUsages                             Counter64,
        	apmPaStatHttpAgentTotalSuccesses                          Counter64,
        	apmPaStatHttpAgentTotalFailures                           Counter64,
        	apmPaStatHttpAgentTotalErrors                             Counter64,
        	apmPaStatHttpAgentTotalSessVars                           Counter64,
        	apmPaStatLdapAgentTotalInstances                          Counter64,
        	apmPaStatLdapAgentTotalUsages                             Counter64,
        	apmPaStatLdapAgentTotalSuccesses                          Counter64,
        	apmPaStatLdapAgentTotalFailures                           Counter64,
        	apmPaStatLdapAgentTotalErrors                             Counter64,
        	apmPaStatLdapAgentTotalSessVars                           Counter64,
        	apmPaStatRadiusAgentTotalInstances                        Counter64,
        	apmPaStatRadiusAgentTotalUsages                           Counter64,
        	apmPaStatRadiusAgentTotalSuccesses                        Counter64,
        	apmPaStatRadiusAgentTotalFailures                         Counter64,
        	apmPaStatRadiusAgentTotalErrors                           Counter64,
        	apmPaStatRadiusAgentTotalSessVars                         Counter64,
        	apmPaStatSecuridAgentTotalInstances                       Counter64,
        	apmPaStatSecuridAgentTotalUsages                          Counter64,
        	apmPaStatSecuridAgentTotalSuccesses                       Counter64,
        	apmPaStatSecuridAgentTotalFailures                        Counter64,
        	apmPaStatSecuridAgentTotalErrors                          Counter64,
        	apmPaStatSecuridAgentTotalSessVars                        Counter64,
        	apmPaStatRadiusAcctAgentTotalInstances                    Counter64,
        	apmPaStatRadiusAcctAgentTotalUsages                       Counter64,
        	apmPaStatRadiusAcctAgentTotalSuccesses                    Counter64,
        	apmPaStatRadiusAcctAgentTotalFailures                     Counter64,
        	apmPaStatRadiusAcctAgentTotalErrors                       Counter64,
        	apmPaStatRadiusAcctAgentTotalSessVars                     Counter64,
        	apmPaStatEpsLinuxFcAgentTotalInstances                    Counter64,
        	apmPaStatEpsLinuxFcAgentTotalUsages                       Counter64,
        	apmPaStatEpsLinuxFcAgentTotalSuccesses                    Counter64,
        	apmPaStatEpsLinuxFcAgentTotalFailures                     Counter64,
        	apmPaStatEpsLinuxFcAgentTotalErrors                       Counter64,
        	apmPaStatEpsLinuxFcAgentTotalSessVars                     Counter64,
        	apmPaStatEpsLinuxPcAgentTotalInstances                    Counter64,
        	apmPaStatEpsLinuxPcAgentTotalUsages                       Counter64,
        	apmPaStatEpsLinuxPcAgentTotalSuccesses                    Counter64,
        	apmPaStatEpsLinuxPcAgentTotalFailures                     Counter64,
        	apmPaStatEpsLinuxPcAgentTotalErrors                       Counter64,
        	apmPaStatEpsLinuxPcAgentTotalSessVars                     Counter64,
        	apmPaStatEpsMacFcAgentTotalInstances                      Counter64,
        	apmPaStatEpsMacFcAgentTotalUsages                         Counter64,
        	apmPaStatEpsMacFcAgentTotalSuccesses                      Counter64,
        	apmPaStatEpsMacFcAgentTotalFailures                       Counter64,
        	apmPaStatEpsMacFcAgentTotalErrors                         Counter64,
        	apmPaStatEpsMacFcAgentTotalSessVars                       Counter64,
        	apmPaStatEpsMacPcAgentTotalInstances                      Counter64,
        	apmPaStatEpsMacPcAgentTotalUsages                         Counter64,
        	apmPaStatEpsMacPcAgentTotalSuccesses                      Counter64,
        	apmPaStatEpsMacPcAgentTotalFailures                       Counter64,
        	apmPaStatEpsMacPcAgentTotalErrors                         Counter64,
        	apmPaStatEpsMacPcAgentTotalSessVars                       Counter64,
        	apmPaStatEpsWinCcAgentTotalInstances                      Counter64,
        	apmPaStatEpsWinCcAgentTotalUsages                         Counter64,
        	apmPaStatEpsWinCcAgentTotalSuccesses                      Counter64,
        	apmPaStatEpsWinCcAgentTotalFailures                       Counter64,
        	apmPaStatEpsWinCcAgentTotalErrors                         Counter64,
        	apmPaStatEpsWinCcAgentTotalSessVars                       Counter64,
        	apmPaStatEpsAvAgentTotalInstances                         Counter64,
        	apmPaStatEpsAvAgentTotalUsages                            Counter64,
        	apmPaStatEpsAvAgentTotalSuccesses                         Counter64,
        	apmPaStatEpsAvAgentTotalFailures                          Counter64,
        	apmPaStatEpsAvAgentTotalErrors                            Counter64,
        	apmPaStatEpsAvAgentTotalSessVars                          Counter64,
        	apmPaStatEpsWinOsInfoAgentTotalInstances                  Counter64,
        	apmPaStatEpsWinOsInfoAgentTotalUsages                     Counter64,
        	apmPaStatEpsWinOsInfoAgentTotalSuccesses                  Counter64,
        	apmPaStatEpsWinOsInfoAgentTotalFailures                   Counter64,
        	apmPaStatEpsWinOsInfoAgentTotalErrors                     Counter64,
        	apmPaStatEpsWinOsInfoAgentTotalSessVars                   Counter64,
        	apmPaStatEpsWinFcAgentTotalInstances                      Counter64,
        	apmPaStatEpsWinFcAgentTotalUsages                         Counter64,
        	apmPaStatEpsWinFcAgentTotalSuccesses                      Counter64,
        	apmPaStatEpsWinFcAgentTotalFailures                       Counter64,
        	apmPaStatEpsWinFcAgentTotalErrors                         Counter64,
        	apmPaStatEpsWinFcAgentTotalSessVars                       Counter64,
        	apmPaStatEpsWinMcAgentTotalInstances                      Counter64,
        	apmPaStatEpsWinMcAgentTotalUsages                         Counter64,
        	apmPaStatEpsWinMcAgentTotalSuccesses                      Counter64,
        	apmPaStatEpsWinMcAgentTotalFailures                       Counter64,
        	apmPaStatEpsWinMcAgentTotalErrors                         Counter64,
        	apmPaStatEpsWinMcAgentTotalSessVars                       Counter64,
        	apmPaStatEpsFwcAgentTotalInstances                        Counter64,
        	apmPaStatEpsFwcAgentTotalUsages                           Counter64,
        	apmPaStatEpsFwcAgentTotalSuccesses                        Counter64,
        	apmPaStatEpsFwcAgentTotalFailures                         Counter64,
        	apmPaStatEpsFwcAgentTotalErrors                           Counter64,
        	apmPaStatEpsFwcAgentTotalSessVars                         Counter64,
        	apmPaStatEpsWinPcTotalInstances                           Counter64,
        	apmPaStatEpsWinPcTotalUsages                              Counter64,
        	apmPaStatEpsWinPcTotalSuccesses                           Counter64,
        	apmPaStatEpsWinPcTotalFailures                            Counter64,
        	apmPaStatEpsWinPcTotalErrors                              Counter64,
        	apmPaStatEpsWinPcTotalSessVars                            Counter64,
        	apmPaStatEpsWinPwTotalInstances                           Counter64,
        	apmPaStatEpsWinPwTotalUsages                              Counter64,
        	apmPaStatEpsWinPwTotalSuccesses                           Counter64,
        	apmPaStatEpsWinPwTotalFailures                            Counter64,
        	apmPaStatEpsWinPwTotalErrors                              Counter64,
        	apmPaStatEpsWinPwTotalSessVars                            Counter64,
        	apmPaStatEpsWinRcAgentTotalInstances                      Counter64,
        	apmPaStatEpsWinRcAgentTotalUsages                         Counter64,
        	apmPaStatEpsWinRcAgentTotalSuccesses                      Counter64,
        	apmPaStatEpsWinRcAgentTotalFailures                       Counter64,
        	apmPaStatEpsWinRcAgentTotalErrors                         Counter64,
        	apmPaStatEpsWinRcAgentTotalSessVars                       Counter64,
        	apmPaStatEpsWinGpAgentTotalInstances                      Counter64,
        	apmPaStatEpsWinGpAgentTotalUsages                         Counter64,
        	apmPaStatEpsWinGpAgentTotalSuccesses                      Counter64,
        	apmPaStatEpsWinGpAgentTotalFailures                       Counter64,
        	apmPaStatEpsWinGpAgentTotalErrors                         Counter64,
        	apmPaStatEpsWinGpAgentTotalSessVars                       Counter64,
        	apmPaStatExternalLogonAgentTotalInstances                 Counter64,
        	apmPaStatExternalLogonAgentTotalUsages                    Counter64,
        	apmPaStatExternalLogonAgentTotalSuccesses                 Counter64,
        	apmPaStatExternalLogonAgentTotalFailures                  Counter64,
        	apmPaStatExternalLogonAgentTotalErrors                    Counter64,
        	apmPaStatExternalLogonAgentTotalSessVars                  Counter64,
        	apmPaStatLogonAgentTotalInstances                         Counter64,
        	apmPaStatLogonAgentTotalUsages                            Counter64,
        	apmPaStatLogonAgentTotalSuccesses                         Counter64,
        	apmPaStatLogonAgentTotalFailures                          Counter64,
        	apmPaStatLogonAgentTotalErrors                            Counter64,
        	apmPaStatLogonAgentTotalSessVars                          Counter64,
        	apmPaStatRaAgentTotalInstances                            Counter64,
        	apmPaStatRaAgentTotalUsages                               Counter64,
        	apmPaStatRaAgentTotalSuccesses                            Counter64,
        	apmPaStatRaAgentTotalFailures                             Counter64,
        	apmPaStatRaAgentTotalErrors                               Counter64,
        	apmPaStatRaAgentTotalSessVars                             Counter64,
        	apmPaStatRdsAgentTotalInstances                           Counter64,
        	apmPaStatRdsAgentTotalUsages                              Counter64,
        	apmPaStatRdsAgentTotalSuccesses                           Counter64,
        	apmPaStatRdsAgentTotalFailures                            Counter64,
        	apmPaStatRdsAgentTotalErrors                              Counter64,
        	apmPaStatRdsAgentTotalSessVars                            Counter64,
        	apmPaStatVaAgentTotalInstances                            Counter64,
        	apmPaStatVaAgentTotalUsages                               Counter64,
        	apmPaStatVaAgentTotalSuccesses                            Counter64,
        	apmPaStatVaAgentTotalFailures                             Counter64,
        	apmPaStatVaAgentTotalErrors                               Counter64,
        	apmPaStatVaAgentTotalSessVars                             Counter64,
        	apmPaStatIeAgentTotalInstances                            Counter64,
        	apmPaStatIeAgentTotalUsages                               Counter64,
        	apmPaStatIeAgentTotalSuccesses                            Counter64,
        	apmPaStatIeAgentTotalFailures                             Counter64,
        	apmPaStatIeAgentTotalErrors                               Counter64,
        	apmPaStatIeAgentTotalSessVars                             Counter64,
        	apmPaStatLoggingAgentTotalInstances                       Counter64,
        	apmPaStatLoggingAgentTotalUsages                          Counter64,
        	apmPaStatLoggingAgentTotalSuccesses                       Counter64,
        	apmPaStatLoggingAgentTotalFailures                        Counter64,
        	apmPaStatLoggingAgentTotalErrors                          Counter64,
        	apmPaStatLoggingAgentTotalSessVars                        Counter64,
        	apmPaStatDecnBoxAgentTotalInstances                       Counter64,
        	apmPaStatDecnBoxAgentTotalUsages                          Counter64,
        	apmPaStatDecnBoxAgentTotalSuccesses                       Counter64,
        	apmPaStatDecnBoxAgentTotalFailures                        Counter64,
        	apmPaStatDecnBoxAgentTotalErrors                          Counter64,
        	apmPaStatDecnBoxAgentTotalSessVars                        Counter64,
        	apmPaStatMesgBoxAgentTotalInstances                       Counter64,
        	apmPaStatMesgBoxAgentTotalUsages                          Counter64,
        	apmPaStatMesgBoxAgentTotalSuccesses                       Counter64,
        	apmPaStatMesgBoxAgentTotalFailures                        Counter64,
        	apmPaStatMesgBoxAgentTotalErrors                          Counter64,
        	apmPaStatMesgBoxAgentTotalSessVars                        Counter64,
        	apmPaStatApdNoResultErrors                                Counter64,
        	apmPaStatApdNoSessionErrors                               Counter64,
        	apmPaStatApdNoDeviceInfoErrors                            Counter64,
        	apmPaStatApdNoTokenErrors                                 Counter64,
        	apmPaStatApdNoSigErrors                                   Counter64,
        	apmPaStatApdTotalMismatchErrors                           Counter64,
        	apmPaStatApdInvalidSigErrors                              Counter64,
        	apmPaStatApdMcPipelineInitErrors                          Counter64,
        	apmPaStatApdMcSetSessVarErrors                            Counter64,
        	apmPaStatApdMcPipelineCloseErrors                         Counter64,
        	apmPaStatApdApResultErrors                                Counter64,
        	apmPaStatApdApInternalErrors                              Counter64,
        	apmPaStatAllowedRequests                                  Counter64,
        	apmPaStatDeniedRequests                                   Counter64,
        	apmPaStatVsName                                           LongDisplayString,
        	apmPaStatSessionsEvalTimedOut                             Counter64,
        	apmPaStatSessionsEstabTimedOut                            Counter64
	}

apmPaStatName OBJECT-TYPE 
	SYNTAX LongDisplayString
	MAX-ACCESS read-only
	STATUS current
	DESCRIPTION
		"The name of an access profile"
	::= { apmPaStatEntry 1 } 

apmPaStatConfigSyncState OBJECT-TYPE 
	SYNTAX Counter64
	MAX-ACCESS read-only
	STATUS	 deprecated
	DESCRIPTION
		"Deprecated!
	    The state of config sync operation"
	::= { apmPaStatEntry 2 } 

apmPaStatTotalSessions OBJECT-TYPE 
	SYNTAX Counter64
	MAX-ACCESS read-only
	STATUS current
	DESCRIPTION
		"The total user sessions in the specified access profile"
	::= { apmPaStatEntry 3 } 

apmPaStatTotalEstablishedStateSessions OBJECT-TYPE 
	SYNTAX Counter64
	MAX-ACCESS read-only
	STATUS current
	DESCRIPTION
		"The total user sessions in the specified access profile"
	::= { apmPaStatEntry 4 } 

apmPaStatCurrentActiveSessions OBJECT-TYPE 
	SYNTAX Counter64
	MAX-ACCESS read-only
	STATUS current
	DESCRIPTION
		"The total active user sessions in the specified access profile"
	::= { apmPaStatEntry 5 } 

apmPaStatCurrentPendingSessions OBJECT-TYPE 
	SYNTAX Counter64
	MAX-ACCESS read-only
	STATUS current
	DESCRIPTION
		"The total user sessions going through access policy evaluation in the specified access profile"
	::= { apmPaStatEntry 6 } 

apmPaStatCurrentCompletedSessions OBJECT-TYPE 
	SYNTAX Counter64
	MAX-ACCESS read-only
	STATUS current
	DESCRIPTION
		"The total user sessions completed access policy evaluation in the specified access profile"
	::= { apmPaStatEntry 7 } 

apmPaStatUserLoggedoutSessions OBJECT-TYPE 
	SYNTAX Counter64
	MAX-ACCESS read-only
	STATUS current
	DESCRIPTION
		"The total sessions logged out by user in the specified access profile"
	::= { apmPaStatEntry 8 } 

apmPaStatAdminTerminatedSessions OBJECT-TYPE 
	SYNTAX Counter64
	MAX-ACCESS read-only
	STATUS current
	DESCRIPTION
		"The total sessions terminated by admin in the specified access profile"
	::= { apmPaStatEntry 9 } 

apmPaStatMiscTerminatedSessions OBJECT-TYPE 
	SYNTAX Counter64
	MAX-ACCESS read-only
	STATUS current
	DESCRIPTION
		"The total sessions terminated by internal errors/conditions in the specified access profile"
	::= { apmPaStatEntry 10 } 

apmPaStatAccessPolicyResultAllow OBJECT-TYPE 
	SYNTAX Counter64
	MAX-ACCESS read-only
	STATUS current
	DESCRIPTION
		"The total sessions resulted allow ending in the specified access profile"
	::= { apmPaStatEntry 11 } 

apmPaStatAccessPolicyResultDeny OBJECT-TYPE 
	SYNTAX Counter64
	MAX-ACCESS read-only
	STATUS current
	DESCRIPTION
		"The total sessions resulted deny ending in the specified access profile"
	::= { apmPaStatEntry 12 } 

apmPaStatAccessPolicyResultRedirect OBJECT-TYPE 
	SYNTAX Counter64
	MAX-ACCESS read-only
	STATUS current
	DESCRIPTION
		"The total sessions redirected to the configured URI after closing the session in the specified access profile"
	::= { apmPaStatEntry 13 } 

apmPaStatAccessPolicyResultRedirectWithSession OBJECT-TYPE 
	SYNTAX Counter64
	MAX-ACCESS read-only
	STATUS current
	DESCRIPTION
		"The total sessions redirected to the configured URI without closing the session in the specified access profile"
	::= { apmPaStatEntry 14 } 

apmPaStatEndingDenyAgentTotalInstances OBJECT-TYPE 
	SYNTAX Counter64
	MAX-ACCESS read-only
	STATUS	 deprecated
	DESCRIPTION
		"Deprecated!
	     The total instances of the ending deny agent in the specified access profile"
	::= { apmPaStatEntry 15 } 

apmPaStatEndingDenyAgentTotalUsages OBJECT-TYPE 
	SYNTAX Counter64
	MAX-ACCESS read-only
	STATUS	 deprecated
	DESCRIPTION
		"Deprecated!
	     The total usages of ending deny agent in the specified access profile"
	::= { apmPaStatEntry 16 } 

apmPaStatEndingDenyAgentTotalSuccesses OBJECT-TYPE 
	SYNTAX Counter64
	MAX-ACCESS read-only
	STATUS	 deprecated
	DESCRIPTION
		"Deprecated!
	     The total success conditions created/reached by the ending deny agent in the specified access profile"
	::= { apmPaStatEntry 17 } 

apmPaStatEndingDenyAgentTotalFailures OBJECT-TYPE 
	SYNTAX Counter64
	MAX-ACCESS read-only
	STATUS	 deprecated
	DESCRIPTION
		"Deprecated!
	     The total failure conditions created/reached by the ending deny agent in the specified access profile"
	::= { apmPaStatEntry 18 } 

apmPaStatEndingDenyAgentTotalErrors OBJECT-TYPE 
	SYNTAX Counter64
	MAX-ACCESS read-only
	STATUS	 deprecated
	DESCRIPTION
		"Deprecated!
	     The total error conditions created/reached by the ending deny agent in the specified access profile"
	::= { apmPaStatEntry 19 } 

apmPaStatEndingDenyAgentTotalSessVars OBJECT-TYPE 
	SYNTAX Counter64
	MAX-ACCESS read-only
	STATUS	 deprecated
	DESCRIPTION
		"Deprecated!
	     The total session variables created by the ending deny agent in the specified access profile"
	::= { apmPaStatEntry 20 } 

apmPaStatEndingRedirectAgentTotalInstances OBJECT-TYPE 
	SYNTAX Counter64
	MAX-ACCESS read-only
	STATUS	 deprecated
	DESCRIPTION
		"Deprecated!
	     The total instances of the ending redirect agent in the specified access profile"
	::= { apmPaStatEntry 21 } 

apmPaStatEndingRedirectAgentTotalUsages OBJECT-TYPE 
	SYNTAX Counter64
	MAX-ACCESS read-only
	STATUS	 deprecated
	DESCRIPTION
		"Deprecated!
	     The total usages of ending redirect agent in the specified access profile"
	::= { apmPaStatEntry 22 } 

apmPaStatEndingRedirectAgentTotalSuccesses OBJECT-TYPE 
	SYNTAX Counter64
	MAX-ACCESS read-only
	STATUS	 deprecated
	DESCRIPTION
		"Deprecated!
	     The total success conditions created/reached by the ending redirect agent in the specified access profile"
	::= { apmPaStatEntry 23 } 

apmPaStatEndingRedirectAgentTotalFailures OBJECT-TYPE 
	SYNTAX Counter64
	MAX-ACCESS read-only
	STATUS	 deprecated
	DESCRIPTION
		"Deprecated!
	     The total failure conditions created/reached by the ending redirect agent in the specified access profile"
	::= { apmPaStatEntry 24 } 

apmPaStatEndingRedirectAgentTotalErrors OBJECT-TYPE 
	SYNTAX Counter64
	MAX-ACCESS read-only
	STATUS	 deprecated
	DESCRIPTION
		"Deprecated!
	     The total error conditions created/reached by the ending redirect agent in the specified access profile"
	::= { apmPaStatEntry 25 } 

apmPaStatEndingRedirectAgentTotalSessVars OBJECT-TYPE 
	SYNTAX Counter64
	MAX-ACCESS read-only
	STATUS	 deprecated
	DESCRIPTION
		"Deprecated!
	     The total session variables created by the ending redirect agent in the specified access profile"
	::= { apmPaStatEntry 26 } 

apmPaStatEndingAllowAgentTotalInstances OBJECT-TYPE 
	SYNTAX Counter64
	MAX-ACCESS read-only
	STATUS	 deprecated
	DESCRIPTION
		"Deprecated!
	     The total instances of the ending allow agent in the specified access profile"
	::= { apmPaStatEntry 27 } 

apmPaStatEndingAllowAgentTotalUsages OBJECT-TYPE 
	SYNTAX Counter64
	MAX-ACCESS read-only
	STATUS	 deprecated
	DESCRIPTION
		"Deprecated!
	     The total usages of ending allow agent in the specified access profile"
	::= { apmPaStatEntry 28 } 

apmPaStatEndingAllowAgentTotalSuccesses OBJECT-TYPE 
	SYNTAX Counter64
	MAX-ACCESS read-only
	STATUS	 deprecated
	DESCRIPTION
		"Deprecated!
	     The total success conditions created/reached by the ending allow agent in the specified access profile"
	::= { apmPaStatEntry 29 } 

apmPaStatEndingAllowAgentTotalFailures OBJECT-TYPE 
	SYNTAX Counter64
	MAX-ACCESS read-only
	STATUS	 deprecated
	DESCRIPTION
		"Deprecated!
	     The total failure conditions created/reached by the ending allow agent in the specified access profile"
	::= { apmPaStatEntry 30 } 

apmPaStatEndingAllowAgentTotalErrors OBJECT-TYPE 
	SYNTAX Counter64
	MAX-ACCESS read-only
	STATUS	 deprecated
	DESCRIPTION
		"Deprecated!
	     The total error conditions created/reached by the ending allow agent in the specified access profile"
	::= { apmPaStatEntry 31 } 

apmPaStatEndingAllowAgentTotalSessVars OBJECT-TYPE 
	SYNTAX Counter64
	MAX-ACCESS read-only
	STATUS	 deprecated
	DESCRIPTION
		"Deprecated!
	     The total session variables created by the ending allow agent in the specified access profile"
	::= { apmPaStatEntry 32 } 

apmPaStatAdAgentTotalInstances OBJECT-TYPE 
	SYNTAX Counter64
	MAX-ACCESS read-only
	STATUS	 deprecated
	DESCRIPTION
		"Deprecated!
	     The total instances of the active directory agent in the specified access profile"
	::= { apmPaStatEntry 33 } 

apmPaStatAdAgentTotalUsages OBJECT-TYPE 
	SYNTAX Counter64
	MAX-ACCESS read-only
	STATUS	 deprecated
	DESCRIPTION
		"Deprecated!
	     The total usages of active directory agent in the specified access profile"
	::= { apmPaStatEntry 34 } 

apmPaStatAdAgentTotalSuccesses OBJECT-TYPE 
	SYNTAX Counter64
	MAX-ACCESS read-only
	STATUS	 deprecated
	DESCRIPTION
		"Deprecated!
	     The total success conditions created/reached by the active directory agent in the specified access profile"
	::= { apmPaStatEntry 35 } 

apmPaStatAdAgentTotalFailures OBJECT-TYPE 
	SYNTAX Counter64
	MAX-ACCESS read-only
	STATUS	 deprecated
	DESCRIPTION
		"Deprecated!
	     The total failure conditions created/reached by the active directory agent in the specified access profile"
	::= { apmPaStatEntry 36 } 

apmPaStatAdAgentTotalErrors OBJECT-TYPE 
	SYNTAX Counter64
	MAX-ACCESS read-only
	STATUS	 deprecated
	DESCRIPTION
		"Deprecated!
	     The total error conditions created/reached by the active directory agent in the specified access profile"
	::= { apmPaStatEntry 37 } 

apmPaStatAdAgentTotalSessVars OBJECT-TYPE 
	SYNTAX Counter64
	MAX-ACCESS read-only
	STATUS	 deprecated
	DESCRIPTION
		"Deprecated!
	     The total session variables created by the active directory agent in the specified access profile"
	::= { apmPaStatEntry 38 } 

apmPaStatClientCertAgentTotalInstances OBJECT-TYPE 
	SYNTAX Counter64
	MAX-ACCESS read-only
	STATUS	 deprecated
	DESCRIPTION
		"Deprecated!
	     The total instances of the client cert agent in the specified access profile"
	::= { apmPaStatEntry 39 } 

apmPaStatClientCertAgentTotalUsages OBJECT-TYPE 
	SYNTAX Counter64
	MAX-ACCESS read-only
	STATUS	 deprecated
	DESCRIPTION
		"Deprecated!
	     The total usages of client cert agent in the specified access profile"
	::= { apmPaStatEntry 40 } 

apmPaStatClientCertAgentTotalSuccesses OBJECT-TYPE 
	SYNTAX Counter64
	MAX-ACCESS read-only
	STATUS	 deprecated
	DESCRIPTION
		"Deprecated!
	     The total success conditions created/reached by the client cert agent in the specified access profile"
	::= { apmPaStatEntry 41 } 

apmPaStatClientCertAgentTotalFailures OBJECT-TYPE 
	SYNTAX Counter64
	MAX-ACCESS read-only
	STATUS	 deprecated
	DESCRIPTION
		"Deprecated!
	     The total failure conditions created/reached by the client cert agent in the specified access profile"
	::= { apmPaStatEntry 42 } 

apmPaStatClientCertAgentTotalErrors OBJECT-TYPE 
	SYNTAX Counter64
	MAX-ACCESS read-only
	STATUS	 deprecated
	DESCRIPTION
		"Deprecated!
	     The total error conditions created/reached by the client cert agent in the specified access profile"
	::= { apmPaStatEntry 43 } 

apmPaStatClientCertAgentTotalSessVars OBJECT-TYPE 
	SYNTAX Counter64
	MAX-ACCESS read-only
	STATUS	 deprecated
	DESCRIPTION
		"Deprecated!
	     The total session variables created by the client cert agent in the specified access profile"
	::= { apmPaStatEntry 44 } 

apmPaStatHttpAgentTotalInstances OBJECT-TYPE 
	SYNTAX Counter64
	MAX-ACCESS read-only
	STATUS	 deprecated
	DESCRIPTION
		"Deprecated!
	     The total instances of the HTTP agent in the specified access profile"
	::= { apmPaStatEntry 45 } 

apmPaStatHttpAgentTotalUsages OBJECT-TYPE 
	SYNTAX Counter64
	MAX-ACCESS read-only
	STATUS	 deprecated
	DESCRIPTION
		"Deprecated!
	     The total usages of HTTP agent in the specified access profile"
	::= { apmPaStatEntry 46 } 

apmPaStatHttpAgentTotalSuccesses OBJECT-TYPE 
	SYNTAX Counter64
	MAX-ACCESS read-only
	STATUS	 deprecated
	DESCRIPTION
		"Deprecated!
	     The total success conditions created/reached by the HTTP agent in the specified access profile"
	::= { apmPaStatEntry 47 } 

apmPaStatHttpAgentTotalFailures OBJECT-TYPE 
	SYNTAX Counter64
	MAX-ACCESS read-only
	STATUS	 deprecated
	DESCRIPTION
		"Deprecated!
	     The total failure conditions created/reached by the HTTP agent in the specified access profile"
	::= { apmPaStatEntry 48 } 

apmPaStatHttpAgentTotalErrors OBJECT-TYPE 
	SYNTAX Counter64
	MAX-ACCESS read-only
	STATUS	 deprecated
	DESCRIPTION
		"Deprecated!
	     The total error conditions created/reached by the HTTP agent in the specified access profile"
	::= { apmPaStatEntry 49 } 

apmPaStatHttpAgentTotalSessVars OBJECT-TYPE 
	SYNTAX Counter64
	MAX-ACCESS read-only
	STATUS	 deprecated
	DESCRIPTION
		"Deprecated!
	     The total session variables created by the HTTP agent in the specified access profile"
	::= { apmPaStatEntry 50 } 

apmPaStatLdapAgentTotalInstances OBJECT-TYPE 
	SYNTAX Counter64
	MAX-ACCESS read-only
	STATUS	 deprecated
	DESCRIPTION
		"Deprecated!
	     The total instances of the LDAP agent in the specified access profile"
	::= { apmPaStatEntry 51 } 

apmPaStatLdapAgentTotalUsages OBJECT-TYPE 
	SYNTAX Counter64
	MAX-ACCESS read-only
	STATUS	 deprecated
	DESCRIPTION
		"Deprecated!
	     The total usages of LDAP agent in the specified access profile"
	::= { apmPaStatEntry 52 } 

apmPaStatLdapAgentTotalSuccesses OBJECT-TYPE 
	SYNTAX Counter64
	MAX-ACCESS read-only
	STATUS	 deprecated
	DESCRIPTION
		"Deprecated!
	     The total success conditions created/reached by the LDAP agent in the specified access profile"
	::= { apmPaStatEntry 53 } 

apmPaStatLdapAgentTotalFailures OBJECT-TYPE 
	SYNTAX Counter64
	MAX-ACCESS read-only
	STATUS	 deprecated
	DESCRIPTION
		"Deprecated!
	     The total failure conditions created/reached by the LDAP agent in the specified access profile"
	::= { apmPaStatEntry 54 } 

apmPaStatLdapAgentTotalErrors OBJECT-TYPE 
	SYNTAX Counter64
	MAX-ACCESS read-only
	STATUS	 deprecated
	DESCRIPTION
		"Deprecated!
	     The total error conditions created/reached by the LDAP agent in the specified access profile"
	::= { apmPaStatEntry 55 } 

apmPaStatLdapAgentTotalSessVars OBJECT-TYPE 
	SYNTAX Counter64
	MAX-ACCESS read-only
	STATUS	 deprecated
	DESCRIPTION
		"Deprecated!
	     The total session variables created by the LDAP agent in the specified access profile"
	::= { apmPaStatEntry 56 } 

apmPaStatRadiusAgentTotalInstances OBJECT-TYPE 
	SYNTAX Counter64
	MAX-ACCESS read-only
	STATUS	 deprecated
	DESCRIPTION
		"Deprecated!
	     The total instances of the Radius agent in the specified access profile"
	::= { apmPaStatEntry 57 } 

apmPaStatRadiusAgentTotalUsages OBJECT-TYPE 
	SYNTAX Counter64
	MAX-ACCESS read-only
	STATUS	 deprecated
	DESCRIPTION
		"Deprecated!
	     The total usages of Radius agent in the specified access profile"
	::= { apmPaStatEntry 58 } 

apmPaStatRadiusAgentTotalSuccesses OBJECT-TYPE 
	SYNTAX Counter64
	MAX-ACCESS read-only
	STATUS	 deprecated
	DESCRIPTION
		"Deprecated!
	     The total success conditions created/reached by the Radius agent in the specified access profile"
	::= { apmPaStatEntry 59 } 

apmPaStatRadiusAgentTotalFailures OBJECT-TYPE 
	SYNTAX Counter64
	MAX-ACCESS read-only
	STATUS	 deprecated
	DESCRIPTION
		"Deprecated!
	     The total failure conditions created/reached by the Radius agent in the specified access profile"
	::= { apmPaStatEntry 60 } 

apmPaStatRadiusAgentTotalErrors OBJECT-TYPE 
	SYNTAX Counter64
	MAX-ACCESS read-only
	STATUS	 deprecated
	DESCRIPTION
		"Deprecated!
	     The total error conditions created/reached by the Radius agent in the specified access profile"
	::= { apmPaStatEntry 61 } 

apmPaStatRadiusAgentTotalSessVars OBJECT-TYPE 
	SYNTAX Counter64
	MAX-ACCESS read-only
	STATUS	 deprecated
	DESCRIPTION
		"Deprecated!
	     The total session variables created by the Radius agent in the specified access profile"
	::= { apmPaStatEntry 62 } 

apmPaStatSecuridAgentTotalInstances OBJECT-TYPE 
	SYNTAX Counter64
	MAX-ACCESS read-only
	STATUS	 deprecated
	DESCRIPTION
		"Deprecated!
	     The total instances of the SecurID agent in the specified access profile"
	::= { apmPaStatEntry 63 } 

apmPaStatSecuridAgentTotalUsages OBJECT-TYPE 
	SYNTAX Counter64
	MAX-ACCESS read-only
	STATUS	 deprecated
	DESCRIPTION
		"Deprecated!
	     The total usages of SecurID agent in the specified access profile"
	::= { apmPaStatEntry 64 } 

apmPaStatSecuridAgentTotalSuccesses OBJECT-TYPE 
	SYNTAX Counter64
	MAX-ACCESS read-only
	STATUS	 deprecated
	DESCRIPTION
		"Deprecated!
	     The total success conditions created/reached by the SecurID agent in the specified access profile"
	::= { apmPaStatEntry 65 } 

apmPaStatSecuridAgentTotalFailures OBJECT-TYPE 
	SYNTAX Counter64
	MAX-ACCESS read-only
	STATUS	 deprecated
	DESCRIPTION
		"Deprecated!
	     The total failure conditions created/reached by the SecurID agent in the specified access profile"
	::= { apmPaStatEntry 66 } 

apmPaStatSecuridAgentTotalErrors OBJECT-TYPE 
	SYNTAX Counter64
	MAX-ACCESS read-only
	STATUS	 deprecated
	DESCRIPTION
		"Deprecated!
	     The total error conditions created/reached by the SecurID agent in the specified access profile"
	::= { apmPaStatEntry 67 } 

apmPaStatSecuridAgentTotalSessVars OBJECT-TYPE 
	SYNTAX Counter64
	MAX-ACCESS read-only
	STATUS	 deprecated
	DESCRIPTION
		"Deprecated!
	     The total session variables created by the SecurID agent in the specified access profile"
	::= { apmPaStatEntry 68 } 

apmPaStatRadiusAcctAgentTotalInstances OBJECT-TYPE 
	SYNTAX Counter64
	MAX-ACCESS read-only
	STATUS	 deprecated
	DESCRIPTION
		"Deprecated!
	     The total instances of the Radius Acct agent in the specified access profile"
	::= { apmPaStatEntry 69 } 

apmPaStatRadiusAcctAgentTotalUsages OBJECT-TYPE 
	SYNTAX Counter64
	MAX-ACCESS read-only
	STATUS	 deprecated
	DESCRIPTION
		"Deprecated!
	     The total usages of Radius Acct agent in the specified access profile"
	::= { apmPaStatEntry 70 } 

apmPaStatRadiusAcctAgentTotalSuccesses OBJECT-TYPE 
	SYNTAX Counter64
	MAX-ACCESS read-only
	STATUS	 deprecated
	DESCRIPTION
		"Deprecated!
	     The total success conditions created/reached by the Radius Acct agent in the specified access profile"
	::= { apmPaStatEntry 71 } 

apmPaStatRadiusAcctAgentTotalFailures OBJECT-TYPE 
	SYNTAX Counter64
	MAX-ACCESS read-only
	STATUS	 deprecated
	DESCRIPTION
		"Deprecated!
	     The total failure conditions created/reached by the Radius Acct agent in the specified access profile"
	::= { apmPaStatEntry 72 } 

apmPaStatRadiusAcctAgentTotalErrors OBJECT-TYPE 
	SYNTAX Counter64
	MAX-ACCESS read-only
	STATUS	 deprecated
	DESCRIPTION
		"Deprecated!
	     The total error conditions created/reached by the Radius Acct agent in the specified access profile"
	::= { apmPaStatEntry 73 } 

apmPaStatRadiusAcctAgentTotalSessVars OBJECT-TYPE 
	SYNTAX Counter64
	MAX-ACCESS read-only
	STATUS	 deprecated
	DESCRIPTION
		"Deprecated!
	     The total session variables created by the Radius Acct agent in the specified access profile"
	::= { apmPaStatEntry 74 } 

apmPaStatEpsLinuxFcAgentTotalInstances OBJECT-TYPE 
	SYNTAX Counter64
	MAX-ACCESS read-only
	STATUS	 deprecated
	DESCRIPTION
		"Deprecated!
	     The total instances of the Linux File Check agent in the specified access profile"
	::= { apmPaStatEntry 75 } 

apmPaStatEpsLinuxFcAgentTotalUsages OBJECT-TYPE 
	SYNTAX Counter64
	MAX-ACCESS read-only
	STATUS	 deprecated
	DESCRIPTION
		"Deprecated!
	     The total usages of Linux File Check agent in the specified access profile"
	::= { apmPaStatEntry 76 } 

apmPaStatEpsLinuxFcAgentTotalSuccesses OBJECT-TYPE 
	SYNTAX Counter64
	MAX-ACCESS read-only
	STATUS	 deprecated
	DESCRIPTION
		"Deprecated!
	     The total success conditions created/reached by the Linux File Check agent in the specified access profile"
	::= { apmPaStatEntry 77 } 

apmPaStatEpsLinuxFcAgentTotalFailures OBJECT-TYPE 
	SYNTAX Counter64
	MAX-ACCESS read-only
	STATUS	 deprecated
	DESCRIPTION
		"Deprecated!
	     The total failure conditions created/reached by the Linux File Check agent in the specified access profile"
	::= { apmPaStatEntry 78 } 

apmPaStatEpsLinuxFcAgentTotalErrors OBJECT-TYPE 
	SYNTAX Counter64
	MAX-ACCESS read-only
	STATUS	 deprecated
	DESCRIPTION
		"Deprecated!
	     The total error conditions created/reached by the Linux File Check agent in the specified access profile"
	::= { apmPaStatEntry 79 } 

apmPaStatEpsLinuxFcAgentTotalSessVars OBJECT-TYPE 
	SYNTAX Counter64
	MAX-ACCESS read-only
	STATUS	 deprecated
	DESCRIPTION
		"Deprecated!
	     The total session variables created by the Linux File Check agent in the specified access profile"
	::= { apmPaStatEntry 80 } 

apmPaStatEpsLinuxPcAgentTotalInstances OBJECT-TYPE 
	SYNTAX Counter64
	MAX-ACCESS read-only
	STATUS	 deprecated
	DESCRIPTION
		"Deprecated!
	     The total instances of the Linux Process Check agent in the specified access profile"
	::= { apmPaStatEntry 81 } 

apmPaStatEpsLinuxPcAgentTotalUsages OBJECT-TYPE 
	SYNTAX Counter64
	MAX-ACCESS read-only
	STATUS	 deprecated
	DESCRIPTION
		"Deprecated!
	     The total usages of Linux Process Check agent in the specified access profile"
	::= { apmPaStatEntry 82 } 

apmPaStatEpsLinuxPcAgentTotalSuccesses OBJECT-TYPE 
	SYNTAX Counter64
	MAX-ACCESS read-only
	STATUS	 deprecated
	DESCRIPTION
		"Deprecated!
	     The total success conditions created/reached by the Linux Process Check agent in the specified access profile"
	::= { apmPaStatEntry 83 } 

apmPaStatEpsLinuxPcAgentTotalFailures OBJECT-TYPE 
	SYNTAX Counter64
	MAX-ACCESS read-only
	STATUS	 deprecated
	DESCRIPTION
		"Deprecated!
	     The total failure conditions created/reached by the Linux Process Check agent in the specified access profile"
	::= { apmPaStatEntry 84 } 

apmPaStatEpsLinuxPcAgentTotalErrors OBJECT-TYPE 
	SYNTAX Counter64
	MAX-ACCESS read-only
	STATUS	 deprecated
	DESCRIPTION
		"Deprecated!
	     The total error conditions created/reached by the Linux Process Check agent in the specified access profile"
	::= { apmPaStatEntry 85 } 

apmPaStatEpsLinuxPcAgentTotalSessVars OBJECT-TYPE 
	SYNTAX Counter64
	MAX-ACCESS read-only
	STATUS	 deprecated
	DESCRIPTION
		"Deprecated!
	     The total session variables created by the Linux Process Check agent in the specified access profile"
	::= { apmPaStatEntry 86 } 

apmPaStatEpsMacFcAgentTotalInstances OBJECT-TYPE 
	SYNTAX Counter64
	MAX-ACCESS read-only
	STATUS	 deprecated
	DESCRIPTION
		"Deprecated!
	     The total instances of the Mac File Check agent in the specified access profile"
	::= { apmPaStatEntry 87 } 

apmPaStatEpsMacFcAgentTotalUsages OBJECT-TYPE 
	SYNTAX Counter64
	MAX-ACCESS read-only
	STATUS	 deprecated
	DESCRIPTION
		"Deprecated!
	     The total usages of Mac File Check agent in the specified access profile"
	::= { apmPaStatEntry 88 } 

apmPaStatEpsMacFcAgentTotalSuccesses OBJECT-TYPE 
	SYNTAX Counter64
	MAX-ACCESS read-only
	STATUS	 deprecated
	DESCRIPTION
		"Deprecated!
	     The total success conditions created/reached by the Mac File Check agent in the specified access profile"
	::= { apmPaStatEntry 89 } 

apmPaStatEpsMacFcAgentTotalFailures OBJECT-TYPE 
	SYNTAX Counter64
	MAX-ACCESS read-only
	STATUS	 deprecated
	DESCRIPTION
		"Deprecated!
	     The total failure conditions created/reached by the Mac File Check agent in the specified access profile"
	::= { apmPaStatEntry 90 } 

apmPaStatEpsMacFcAgentTotalErrors OBJECT-TYPE 
	SYNTAX Counter64
	MAX-ACCESS read-only
	STATUS	 deprecated
	DESCRIPTION
		"Deprecated!
	     The total error conditions created/reached by the Mac File Check agent in the specified access profile"
	::= { apmPaStatEntry 91 } 

apmPaStatEpsMacFcAgentTotalSessVars OBJECT-TYPE 
	SYNTAX Counter64
	MAX-ACCESS read-only
	STATUS	 deprecated
	DESCRIPTION
		"Deprecated!
	     The total session variables created by the Mac File Check agent in the specified access profile"
	::= { apmPaStatEntry 92 } 

apmPaStatEpsMacPcAgentTotalInstances OBJECT-TYPE 
	SYNTAX Counter64
	MAX-ACCESS read-only
	STATUS	 deprecated
	DESCRIPTION
		"Deprecated!
	    The total instances of the Mac Process Check agent in the specified access profile"
	::= { apmPaStatEntry 93 } 

apmPaStatEpsMacPcAgentTotalUsages OBJECT-TYPE 
	SYNTAX Counter64
	MAX-ACCESS read-only
	STATUS	 deprecated
	DESCRIPTION
		"Deprecated!
	    The total usages of Mac Process Check agent in the specified access profile"
	::= { apmPaStatEntry 94 } 

apmPaStatEpsMacPcAgentTotalSuccesses OBJECT-TYPE 
	SYNTAX Counter64
	MAX-ACCESS read-only
	STATUS	 deprecated
	DESCRIPTION
		"Deprecated!
	    The total success conditions created/reached by the Mac Process Check agent in the specified access profile"
	::= { apmPaStatEntry 95 } 

apmPaStatEpsMacPcAgentTotalFailures OBJECT-TYPE 
	SYNTAX Counter64
	MAX-ACCESS read-only
	STATUS	 deprecated
	DESCRIPTION
		"Deprecated!
	    The total failure conditions created/reached by the Mac Process Check agent in the specified access profile"
	::= { apmPaStatEntry 96 } 

apmPaStatEpsMacPcAgentTotalErrors OBJECT-TYPE 
	SYNTAX Counter64
	MAX-ACCESS read-only
	STATUS	 deprecated
	DESCRIPTION
		"Deprecated!
	    The total error conditions created/reached by the Mac Process Check agent in the specified access profile"
	::= { apmPaStatEntry 97 } 

apmPaStatEpsMacPcAgentTotalSessVars OBJECT-TYPE 
	SYNTAX Counter64
	MAX-ACCESS read-only
	STATUS	 deprecated
	DESCRIPTION
		"Deprecated!
	    The total session variables created by the Mac Process Check agent in the specified access profile"
	::= { apmPaStatEntry 98 } 

apmPaStatEpsWinCcAgentTotalInstances OBJECT-TYPE 
	SYNTAX Counter64
	MAX-ACCESS read-only
	STATUS	 deprecated
	DESCRIPTION
		"Deprecated!
	    The total instances of the Windows Browser Cache Cleaner agent in the specified access profile"
	::= { apmPaStatEntry 99 } 

apmPaStatEpsWinCcAgentTotalUsages OBJECT-TYPE 
	SYNTAX Counter64
	MAX-ACCESS read-only
	STATUS	 deprecated
	DESCRIPTION
		"Deprecated!
	    The total usages of Windows Browser Cache Cleaner agent in the specified access profile"
	::= { apmPaStatEntry 100 } 

apmPaStatEpsWinCcAgentTotalSuccesses OBJECT-TYPE 
	SYNTAX Counter64
	MAX-ACCESS read-only
	STATUS	 deprecated
	DESCRIPTION
		"Deprecated!
	    The total success conditions created/reached by the Windows Browser Cache Cleaner agent in the specified access profile"
	::= { apmPaStatEntry 101 } 

apmPaStatEpsWinCcAgentTotalFailures OBJECT-TYPE 
	SYNTAX Counter64
	MAX-ACCESS read-only
	STATUS	 deprecated
	DESCRIPTION
		"Deprecated!
	    The total failure conditions created/reached by the Windows Browser Cache Cleaner agent in the specified access profile"
	::= { apmPaStatEntry 102 } 

apmPaStatEpsWinCcAgentTotalErrors OBJECT-TYPE 
	SYNTAX Counter64
	MAX-ACCESS read-only
	STATUS	 deprecated
	DESCRIPTION
		"Deprecated!
	    The total error conditions created/reached by the Windows Browser Cache Cleaner agent in the specified access profile"
	::= { apmPaStatEntry 103 } 

apmPaStatEpsWinCcAgentTotalSessVars OBJECT-TYPE 
	SYNTAX Counter64
	MAX-ACCESS read-only
	STATUS	 deprecated
	DESCRIPTION
		"Deprecated!
	    The total session variables created by the Windows Browser Cache Cleaner agent in the specified access profile"
	::= { apmPaStatEntry 104 } 

apmPaStatEpsAvAgentTotalInstances OBJECT-TYPE 
	SYNTAX Counter64
	MAX-ACCESS read-only
	STATUS	 deprecated
	DESCRIPTION
		"Deprecated!
	    The total instances of the Windows Antivirus Check agent in the specified access profile"
	::= { apmPaStatEntry 105 } 

apmPaStatEpsAvAgentTotalUsages OBJECT-TYPE 
	SYNTAX Counter64
	MAX-ACCESS read-only
	STATUS	 deprecated
	DESCRIPTION
		"Deprecated!
	    The total usages of Windows Antivirus Check agent in the specified access profile"
	::= { apmPaStatEntry 106 } 

apmPaStatEpsAvAgentTotalSuccesses OBJECT-TYPE 
	SYNTAX Counter64
	MAX-ACCESS read-only
	STATUS	 deprecated
	DESCRIPTION
		"Deprecated!
	    The total success conditions created/reached by the Windows Antivirus Check agent in the specified access profile"
	::= { apmPaStatEntry 107 } 

apmPaStatEpsAvAgentTotalFailures OBJECT-TYPE 
	SYNTAX Counter64
	MAX-ACCESS read-only
	STATUS	 deprecated
	DESCRIPTION
		"Deprecated!
	    The total failure conditions created/reached by the Windows Antivirus Check agent in the specified access profile"
	::= { apmPaStatEntry 108 } 

apmPaStatEpsAvAgentTotalErrors OBJECT-TYPE 
	SYNTAX Counter64
	MAX-ACCESS read-only
	STATUS	 deprecated
	DESCRIPTION
		"Deprecated!
	    The total error conditions created/reached by the Windows Antivirus Check agent in the specified access profile"
	::= { apmPaStatEntry 109 } 

apmPaStatEpsAvAgentTotalSessVars OBJECT-TYPE 
	SYNTAX Counter64
	MAX-ACCESS read-only
	STATUS	 deprecated
	DESCRIPTION
		"Deprecated!
	    The total session variables created by the Windows Antivirus Check agent in the specified access profile"
	::= { apmPaStatEntry 110 } 

apmPaStatEpsWinOsInfoAgentTotalInstances OBJECT-TYPE 
	SYNTAX Counter64
	MAX-ACCESS read-only
	STATUS	 deprecated
	DESCRIPTION
		"Deprecated!
	    The total instances of the Windows OS Info Check agent in the specified access profile"
	::= { apmPaStatEntry 111 } 

apmPaStatEpsWinOsInfoAgentTotalUsages OBJECT-TYPE 
	SYNTAX Counter64
	MAX-ACCESS read-only
	STATUS	 deprecated
	DESCRIPTION
		"Deprecated!
	    The total usages of Windows OS Info Check agent in the specified access profile"
	::= { apmPaStatEntry 112 } 

apmPaStatEpsWinOsInfoAgentTotalSuccesses OBJECT-TYPE 
	SYNTAX Counter64
	MAX-ACCESS read-only
	STATUS	 deprecated
	DESCRIPTION
		"Deprecated!
	    The total success conditions created/reached by the Windows OS Info Check agent in the specified access profile"
	::= { apmPaStatEntry 113 } 

apmPaStatEpsWinOsInfoAgentTotalFailures OBJECT-TYPE 
	SYNTAX Counter64
	MAX-ACCESS read-only
	STATUS	 deprecated
	DESCRIPTION
		"Deprecated!
	    The total failure conditions created/reached by the Windows OS Info Check agent in the specified access profile"
	::= { apmPaStatEntry 114 } 

apmPaStatEpsWinOsInfoAgentTotalErrors OBJECT-TYPE 
	SYNTAX Counter64
	MAX-ACCESS read-only
	STATUS	 deprecated
	DESCRIPTION
		"Deprecated!
	    The total error conditions created/reached by the Windows OS Info Check agent in the specified access profile"
	::= { apmPaStatEntry 115 } 

apmPaStatEpsWinOsInfoAgentTotalSessVars OBJECT-TYPE 
	SYNTAX Counter64
	MAX-ACCESS read-only
	STATUS	 deprecated
	DESCRIPTION
		"Deprecated!
	    The total session variables created by the Windows OS Info Check agent in the specified access profile"
	::= { apmPaStatEntry 116 } 

apmPaStatEpsWinFcAgentTotalInstances OBJECT-TYPE 
	SYNTAX Counter64
	MAX-ACCESS read-only
	STATUS	 deprecated
	DESCRIPTION
		"Deprecated!
	    The total instances of the Windows File Check agent in the specified access profile"
	::= { apmPaStatEntry 117 } 

apmPaStatEpsWinFcAgentTotalUsages OBJECT-TYPE 
	SYNTAX Counter64
	MAX-ACCESS read-only
	STATUS	 deprecated
	DESCRIPTION
		"Deprecated!
	    The total usages of Windows File Check agent in the specified access profile"
	::= { apmPaStatEntry 118 } 

apmPaStatEpsWinFcAgentTotalSuccesses OBJECT-TYPE 
	SYNTAX Counter64
	MAX-ACCESS read-only
	STATUS	 deprecated
	DESCRIPTION
		"Deprecated!
	    The total success conditions created/reached by the Windows File Check agent in the specified access profile"
	::= { apmPaStatEntry 119 } 

apmPaStatEpsWinFcAgentTotalFailures OBJECT-TYPE 
	SYNTAX Counter64
	MAX-ACCESS read-only
	STATUS	 deprecated
	DESCRIPTION
		"Deprecated!
	    The total failure conditions created/reached by the Windows File Check agent in the specified access profile"
	::= { apmPaStatEntry 120 } 

apmPaStatEpsWinFcAgentTotalErrors OBJECT-TYPE 
	SYNTAX Counter64
	MAX-ACCESS read-only
	STATUS	 deprecated
	DESCRIPTION
		"Deprecated!
	    The total error conditions created/reached by the Windows File Check agent in the specified access profile"
	::= { apmPaStatEntry 121 } 

apmPaStatEpsWinFcAgentTotalSessVars OBJECT-TYPE 
	SYNTAX Counter64
	MAX-ACCESS read-only
	STATUS	 deprecated
	DESCRIPTION
		"Deprecated!
	    The total session variables created by the Windows File Check agent in the specified access profile"
	::= { apmPaStatEntry 122 } 

apmPaStatEpsWinMcAgentTotalInstances OBJECT-TYPE 
	SYNTAX Counter64
	MAX-ACCESS read-only
	STATUS	 deprecated
	DESCRIPTION
		"Deprecated!
	    The total instances of the Windows MachineCert Check agent in the specified access profile"
	::= { apmPaStatEntry 123 } 

apmPaStatEpsWinMcAgentTotalUsages OBJECT-TYPE 
	SYNTAX Counter64
	MAX-ACCESS read-only
	STATUS	 deprecated
	DESCRIPTION
		"Deprecated!
	    The total usages of Windows MachineCert Check agent in the specified access profile"
	::= { apmPaStatEntry 124 } 

apmPaStatEpsWinMcAgentTotalSuccesses OBJECT-TYPE 
	SYNTAX Counter64
	MAX-ACCESS read-only
	STATUS	 deprecated
	DESCRIPTION
		"Deprecated!
	    The total success conditions created/reached by the Windows MachineCert Check agent in the specified access profile"
	::= { apmPaStatEntry 125 } 

apmPaStatEpsWinMcAgentTotalFailures OBJECT-TYPE 
	SYNTAX Counter64
	MAX-ACCESS read-only
	STATUS	 deprecated
	DESCRIPTION
		"Deprecated!
	    The total failure conditions created/reached by the Windows MachineCert Check agent in the specified access profile"
	::= { apmPaStatEntry 126 } 

apmPaStatEpsWinMcAgentTotalErrors OBJECT-TYPE 
	SYNTAX Counter64
	MAX-ACCESS read-only
	STATUS	 deprecated
	DESCRIPTION
		"Deprecated!
	    The total error conditions created/reached by the Windows MachineCert Check agent in the specified access profile"
	::= { apmPaStatEntry 127 } 

apmPaStatEpsWinMcAgentTotalSessVars OBJECT-TYPE 
	SYNTAX Counter64
	MAX-ACCESS read-only
	STATUS	 deprecated
	DESCRIPTION
		"Deprecated!
	    The total session variables created by the Windows MachineCert Check agent in the specified access profile"
	::= { apmPaStatEntry 128 } 

apmPaStatEpsFwcAgentTotalInstances OBJECT-TYPE 
	SYNTAX Counter64
	MAX-ACCESS read-only
	STATUS	 deprecated
	DESCRIPTION
		"Deprecated!
	    The total instances of the  Firewall Check agent in the specified access profile"
	::= { apmPaStatEntry 129 } 

apmPaStatEpsFwcAgentTotalUsages OBJECT-TYPE 
	SYNTAX Counter64
	MAX-ACCESS read-only
	STATUS	 deprecated
	DESCRIPTION
		"Deprecated!
	    The total usages of  Firewall Check agent in the specified access profile"
	::= { apmPaStatEntry 130 } 

apmPaStatEpsFwcAgentTotalSuccesses OBJECT-TYPE 
	SYNTAX Counter64
	MAX-ACCESS read-only
	STATUS	 deprecated
	DESCRIPTION
		"Deprecated!
	    The total success conditions created/reached by the  Firewall Check agent in the specified access profile"
	::= { apmPaStatEntry 131 } 

apmPaStatEpsFwcAgentTotalFailures OBJECT-TYPE 
	SYNTAX Counter64
	MAX-ACCESS read-only
	STATUS	 deprecated
	DESCRIPTION
		"Deprecated!
	    The total failure conditions created/reached by the  Firewall Check agent in the specified access profile"
	::= { apmPaStatEntry 132 } 

apmPaStatEpsFwcAgentTotalErrors OBJECT-TYPE 
	SYNTAX Counter64
	MAX-ACCESS read-only
	STATUS	 deprecated
	DESCRIPTION
		"Deprecated!
	    The total error conditions created/reached by the  Firewall Check agent in the specified access profile"
	::= { apmPaStatEntry 133 } 

apmPaStatEpsFwcAgentTotalSessVars OBJECT-TYPE 
	SYNTAX Counter64
	MAX-ACCESS read-only
	STATUS	 deprecated
	DESCRIPTION
		"Deprecated!
	    The total session variables created by the  Firewall Check agent in the specified access profile"
	::= { apmPaStatEntry 134 } 

apmPaStatEpsWinPcTotalInstances OBJECT-TYPE 
	SYNTAX Counter64
	MAX-ACCESS read-only
	STATUS	 deprecated
	DESCRIPTION
		"Deprecated!
	    The total instances of the Windows Process Check agent in the specified access profile"
	::= { apmPaStatEntry 135 } 

apmPaStatEpsWinPcTotalUsages OBJECT-TYPE 
	SYNTAX Counter64
	MAX-ACCESS read-only
	STATUS	 deprecated
	DESCRIPTION
		"Deprecated!
	    The total usages of Windows Process Check agent in the specified access profile"
	::= { apmPaStatEntry 136 } 

apmPaStatEpsWinPcTotalSuccesses OBJECT-TYPE 
	SYNTAX Counter64
	MAX-ACCESS read-only
	STATUS	 deprecated
	DESCRIPTION
		"Deprecated!
	    The total success conditions created/reached by the Windows Process Check agent in the specified access profile"
	::= { apmPaStatEntry 137 } 

apmPaStatEpsWinPcTotalFailures OBJECT-TYPE 
	SYNTAX Counter64
	MAX-ACCESS read-only
	STATUS	 deprecated
	DESCRIPTION
		"Deprecated!
	    The total failure conditions created/reached by the Windows Process Check agent in the specified access profile"
	::= { apmPaStatEntry 138 } 

apmPaStatEpsWinPcTotalErrors OBJECT-TYPE 
	SYNTAX Counter64
	MAX-ACCESS read-only
	STATUS	 deprecated
	DESCRIPTION
		"Deprecated!
	    The total error conditions created/reached by the Windows Process Check agent in the specified access profile"
	::= { apmPaStatEntry 139 } 

apmPaStatEpsWinPcTotalSessVars OBJECT-TYPE 
	SYNTAX Counter64
	MAX-ACCESS read-only
	STATUS	 deprecated
	DESCRIPTION
		"Deprecated!
	    The total session variables created by the Windows Process Check agent in the specified access profile"
	::= { apmPaStatEntry 140 } 

apmPaStatEpsWinPwTotalInstances OBJECT-TYPE 
	SYNTAX Counter64
	MAX-ACCESS read-only
	STATUS	 deprecated
	DESCRIPTION
		"Deprecated!
	    The total instances of the Windows Protected Workspace agent in the specified access profile"
	::= { apmPaStatEntry 141 } 

apmPaStatEpsWinPwTotalUsages OBJECT-TYPE 
	SYNTAX Counter64
	MAX-ACCESS read-only
	STATUS	 deprecated
	DESCRIPTION
		"Deprecated!
	    The total usages of Windows Protected Workspace agent in the specified access profile"
	::= { apmPaStatEntry 142 } 

apmPaStatEpsWinPwTotalSuccesses OBJECT-TYPE 
	SYNTAX Counter64
	MAX-ACCESS read-only
	STATUS	 deprecated
	DESCRIPTION
		"Deprecated!
	    The total success conditions created/reached by the Windows Protected Workspace agent in the specified access profile"
	::= { apmPaStatEntry 143 } 

apmPaStatEpsWinPwTotalFailures OBJECT-TYPE 
	SYNTAX Counter64
	MAX-ACCESS read-only
	STATUS	 deprecated
	DESCRIPTION
		"Deprecated!
	    The total failure conditions created/reached by the Windows Protected Workspace agent in the specified access profile"
	::= { apmPaStatEntry 144 } 

apmPaStatEpsWinPwTotalErrors OBJECT-TYPE 
	SYNTAX Counter64
	MAX-ACCESS read-only
	STATUS	 deprecated
	DESCRIPTION
		"Deprecated!
	    The total error conditions created/reached by the Windows Protected Workspace agent in the specified access profile"
	::= { apmPaStatEntry 145 } 

apmPaStatEpsWinPwTotalSessVars OBJECT-TYPE 
	SYNTAX Counter64
	MAX-ACCESS read-only
	STATUS	 deprecated
	DESCRIPTION
		"Deprecated!
	    The total session variables created by the Windows Protected Workspace agent in the specified access profile"
	::= { apmPaStatEntry 146 } 

apmPaStatEpsWinRcAgentTotalInstances OBJECT-TYPE 
	SYNTAX Counter64
	MAX-ACCESS read-only
	STATUS	 deprecated
	DESCRIPTION
		"Deprecated!
	    The total instances of the Windows Process Check agent in the specified access profile"
	::= { apmPaStatEntry 147 } 

apmPaStatEpsWinRcAgentTotalUsages OBJECT-TYPE 
	SYNTAX Counter64
	MAX-ACCESS read-only
	STATUS	 deprecated
	DESCRIPTION
		"Deprecated!
	    The total usages of Windows Process Check agent in the specified access profile"
	::= { apmPaStatEntry 148 } 

apmPaStatEpsWinRcAgentTotalSuccesses OBJECT-TYPE 
	SYNTAX Counter64
	MAX-ACCESS read-only
	STATUS	 deprecated
	DESCRIPTION
		"Deprecated!
	    The total success conditions created/reached by the Windows Process Check agent in the specified access profile"
	::= { apmPaStatEntry 149 } 

apmPaStatEpsWinRcAgentTotalFailures OBJECT-TYPE 
	SYNTAX Counter64
	MAX-ACCESS read-only
	STATUS	 deprecated
	DESCRIPTION
		"Deprecated!
	    The total failure conditions created/reached by the Windows Process Check agent in the specified access profile"
	::= { apmPaStatEntry 150 } 

apmPaStatEpsWinRcAgentTotalErrors OBJECT-TYPE 
	SYNTAX Counter64
	MAX-ACCESS read-only
	STATUS	 deprecated
	DESCRIPTION
		"Deprecated!
	    The total error conditions created/reached by the Windows Process Check agent in the specified access profile"
	::= { apmPaStatEntry 151 } 

apmPaStatEpsWinRcAgentTotalSessVars OBJECT-TYPE 
	SYNTAX Counter64
	MAX-ACCESS read-only
	STATUS	 deprecated
	DESCRIPTION
		"Deprecated!
	    The total session variables created by the Windows Process Check agent in the specified access profile"
	::= { apmPaStatEntry 152 } 

apmPaStatEpsWinGpAgentTotalInstances OBJECT-TYPE 
	SYNTAX Counter64
	MAX-ACCESS read-only
	STATUS	 deprecated
	DESCRIPTION
		"Deprecated!
	    The total instances of the Windows Group Policy agent in the specified access profile"
	::= { apmPaStatEntry 153 } 

apmPaStatEpsWinGpAgentTotalUsages OBJECT-TYPE 
	SYNTAX Counter64
	MAX-ACCESS read-only
	STATUS	 deprecated
	DESCRIPTION
		"Deprecated!
	    The total usages of Windows Group Policy agent in the specified access profile"
	::= { apmPaStatEntry 154 } 

apmPaStatEpsWinGpAgentTotalSuccesses OBJECT-TYPE 
	SYNTAX Counter64
	MAX-ACCESS read-only
	STATUS	 deprecated
	DESCRIPTION
		"Deprecated!
	    The total success conditions created/reached by the Windows Group Policy agent in the specified access profile"
	::= { apmPaStatEntry 155 } 

apmPaStatEpsWinGpAgentTotalFailures OBJECT-TYPE 
	SYNTAX Counter64
	MAX-ACCESS read-only
	STATUS	 deprecated
	DESCRIPTION
		"Deprecated!
	    The total failure conditions created/reached by the Windows Group Policy agent in the specified access profile"
	::= { apmPaStatEntry 156 } 

apmPaStatEpsWinGpAgentTotalErrors OBJECT-TYPE 
	SYNTAX Counter64
	MAX-ACCESS read-only
	STATUS	 deprecated
	DESCRIPTION
		"Deprecated!
	    The total error conditions created/reached by the Windows Group Policy agent in the specified access profile"
	::= { apmPaStatEntry 157 } 

apmPaStatEpsWinGpAgentTotalSessVars OBJECT-TYPE 
	SYNTAX Counter64
	MAX-ACCESS read-only
	STATUS	 deprecated
	DESCRIPTION
		"Deprecated!
	    The total session variables created by the Windows Group Policy agent in the specified access profile"
	::= { apmPaStatEntry 158 } 

apmPaStatExternalLogonAgentTotalInstances OBJECT-TYPE 
	SYNTAX Counter64
	MAX-ACCESS read-only
	STATUS	 deprecated
	DESCRIPTION
		"Deprecated!
	    The total instances of the External Logon page agent in the specified access profile"
	::= { apmPaStatEntry 159 } 

apmPaStatExternalLogonAgentTotalUsages OBJECT-TYPE 
	SYNTAX Counter64
	MAX-ACCESS read-only
	STATUS	 deprecated
	DESCRIPTION
		"Deprecated!
	    The total usages of External Logon page agent in the specified access profile"
	::= { apmPaStatEntry 160 } 

apmPaStatExternalLogonAgentTotalSuccesses OBJECT-TYPE 
	SYNTAX Counter64
	MAX-ACCESS read-only
	STATUS	 deprecated
	DESCRIPTION
		"Deprecated!
	    The total success conditions created/reached by the External Logon page agent in the specified access profile"
	::= { apmPaStatEntry 161 } 

apmPaStatExternalLogonAgentTotalFailures OBJECT-TYPE 
	SYNTAX Counter64
	MAX-ACCESS read-only
	STATUS	 deprecated
	DESCRIPTION
		"Deprecated!
	    The total failure conditions created/reached by the External Logon page agent in the specified access profile"
	::= { apmPaStatEntry 162 } 

apmPaStatExternalLogonAgentTotalErrors OBJECT-TYPE 
	SYNTAX Counter64
	MAX-ACCESS read-only
	STATUS	 deprecated
	DESCRIPTION
		"Deprecated!
	    The total error conditions created/reached by the External Logon page agent in the specified access profile"
	::= { apmPaStatEntry 163 } 

apmPaStatExternalLogonAgentTotalSessVars OBJECT-TYPE 
	SYNTAX Counter64
	MAX-ACCESS read-only
	STATUS	 deprecated
	DESCRIPTION
		"Deprecated!
	    The total session variables created by the External Logon page agent in the specified access profile"
	::= { apmPaStatEntry 164 } 

apmPaStatLogonAgentTotalInstances OBJECT-TYPE 
	SYNTAX Counter64
	MAX-ACCESS read-only
	STATUS	 deprecated
	DESCRIPTION
		"Deprecated!
	    The total instances of the Logon page agent in the specified access profile"
	::= { apmPaStatEntry 165 } 

apmPaStatLogonAgentTotalUsages OBJECT-TYPE 
	SYNTAX Counter64
	MAX-ACCESS read-only
	STATUS	 deprecated
	DESCRIPTION
		"Deprecated!
	    The total usages of Logon page agent in the specified access profile"
	::= { apmPaStatEntry 166 } 

apmPaStatLogonAgentTotalSuccesses OBJECT-TYPE 
	SYNTAX Counter64
	MAX-ACCESS read-only
	STATUS	 deprecated
	DESCRIPTION
		"Deprecated!
	    The total success conditions created/reached by the Logon page agent in the specified access profile"
	::= { apmPaStatEntry 167 } 

apmPaStatLogonAgentTotalFailures OBJECT-TYPE 
	SYNTAX Counter64
	MAX-ACCESS read-only
	STATUS	 deprecated
	DESCRIPTION
		"Deprecated!
	    The total failure conditions created/reached by the Logon page agent in the specified access profile"
	::= { apmPaStatEntry 168 } 

apmPaStatLogonAgentTotalErrors OBJECT-TYPE 
	SYNTAX Counter64
	MAX-ACCESS read-only
	STATUS	 deprecated
	DESCRIPTION
		"Deprecated!
	    The total error conditions created/reached by the Logon page agent in the specified access profile"
	::= { apmPaStatEntry 169 } 

apmPaStatLogonAgentTotalSessVars OBJECT-TYPE 
	SYNTAX Counter64
	MAX-ACCESS read-only
	STATUS	 deprecated
	DESCRIPTION
		"Deprecated!
	    The total session variables created by the Logon page agent in the specified access profile"
	::= { apmPaStatEntry 170 } 

apmPaStatRaAgentTotalInstances OBJECT-TYPE 
	SYNTAX Counter64
	MAX-ACCESS read-only
	STATUS	 deprecated
	DESCRIPTION
		"Deprecated!
	    The total instances of the Resource Assignment agent in the specified access profile"
	::= { apmPaStatEntry 171 } 

apmPaStatRaAgentTotalUsages OBJECT-TYPE 
	SYNTAX Counter64
	MAX-ACCESS read-only
	STATUS	 deprecated
	DESCRIPTION
		"Deprecated!
	    The total usages of Resource Assignment agent in the specified access profile"
	::= { apmPaStatEntry 172 } 

apmPaStatRaAgentTotalSuccesses OBJECT-TYPE 
	SYNTAX Counter64
	MAX-ACCESS read-only
	STATUS	 deprecated
	DESCRIPTION
		"Deprecated!
	    The total success conditions created/reached by the Resource Assignment agent in the specified access profile"
	::= { apmPaStatEntry 173 } 

apmPaStatRaAgentTotalFailures OBJECT-TYPE 
	SYNTAX Counter64
	MAX-ACCESS read-only
	STATUS	 deprecated
	DESCRIPTION
		"Deprecated!
	    The total failure conditions created/reached by the Resource Assignment agent in the specified access profile"
	::= { apmPaStatEntry 174 } 

apmPaStatRaAgentTotalErrors OBJECT-TYPE 
	SYNTAX Counter64
	MAX-ACCESS read-only
	STATUS	 deprecated
	DESCRIPTION
		"Deprecated!
	    The total error conditions created/reached by the Resource Assignment agent in the specified access profile"
	::= { apmPaStatEntry 175 } 

apmPaStatRaAgentTotalSessVars OBJECT-TYPE 
	SYNTAX Counter64
	MAX-ACCESS read-only
	STATUS	 deprecated
	DESCRIPTION
		"Deprecated!
	    The total session variables created by the Resource Assignment agent in the specified access profile"
	::= { apmPaStatEntry 176 } 

apmPaStatRdsAgentTotalInstances OBJECT-TYPE 
	SYNTAX Counter64
	MAX-ACCESS read-only
	STATUS	 deprecated
	DESCRIPTION
		"Deprecated!
	    The total instances of the Route Domain Selection agent in the specified access profile"
	::= { apmPaStatEntry 177 } 

apmPaStatRdsAgentTotalUsages OBJECT-TYPE 
	SYNTAX Counter64
	MAX-ACCESS read-only
	STATUS	 deprecated
	DESCRIPTION
		"Deprecated!
	    The total usages of Route Domain Selection agent in the specified access profile"
	::= { apmPaStatEntry 178 } 

apmPaStatRdsAgentTotalSuccesses OBJECT-TYPE 
	SYNTAX Counter64
	MAX-ACCESS read-only
	STATUS	 deprecated
	DESCRIPTION
		"Deprecated!
	    The total success conditions created/reached by the Route Domain Selection agent in the specified access profile"
	::= { apmPaStatEntry 179 } 

apmPaStatRdsAgentTotalFailures OBJECT-TYPE 
	SYNTAX Counter64
	MAX-ACCESS read-only
	STATUS	 deprecated
	DESCRIPTION
		"Deprecated!
	    The total failure conditions created/reached by the Route Domain Selection agent in the specified access profile"
	::= { apmPaStatEntry 180 } 

apmPaStatRdsAgentTotalErrors OBJECT-TYPE 
	SYNTAX Counter64
	MAX-ACCESS read-only
	STATUS	 deprecated
	DESCRIPTION
		"Deprecated!
	    The total error conditions created/reached by the Route Domain Selection agent in the specified access profile"
	::= { apmPaStatEntry 181 } 

apmPaStatRdsAgentTotalSessVars OBJECT-TYPE 
	SYNTAX Counter64
	MAX-ACCESS read-only
	STATUS	 deprecated
	DESCRIPTION
		"Deprecated!
	    The total session variables created by the Route Domain Selection agent in the specified access profile"
	::= { apmPaStatEntry 182 } 

apmPaStatVaAgentTotalInstances OBJECT-TYPE 
	SYNTAX Counter64
	MAX-ACCESS read-only
	STATUS	 deprecated
	DESCRIPTION
		"Deprecated!
	    The total instances of the Variable Assignment agent in the specified access profile"
	::= { apmPaStatEntry 183 } 

apmPaStatVaAgentTotalUsages OBJECT-TYPE 
	SYNTAX Counter64
	MAX-ACCESS read-only
	STATUS	 deprecated
	DESCRIPTION
		"Deprecated!
	    The total usages of Variable Assignment agent in the specified access profile"
	::= { apmPaStatEntry 184 } 

apmPaStatVaAgentTotalSuccesses OBJECT-TYPE 
	SYNTAX Counter64
	MAX-ACCESS read-only
	STATUS	 deprecated
	DESCRIPTION
		"Deprecated!
	    The total success conditions created/reached by the Variable Assignment agent in the specified access profile"
	::= { apmPaStatEntry 185 } 

apmPaStatVaAgentTotalFailures OBJECT-TYPE 
	SYNTAX Counter64
	MAX-ACCESS read-only
	STATUS	 deprecated
	DESCRIPTION
		"Deprecated!
	    The total failure conditions created/reached by the Variable Assignment agent in the specified access profile"
	::= { apmPaStatEntry 186 } 

apmPaStatVaAgentTotalErrors OBJECT-TYPE 
	SYNTAX Counter64
	MAX-ACCESS read-only
	STATUS	 deprecated
	DESCRIPTION
		"Deprecated!
	    The total error conditions created/reached by the Variable Assignment agent in the specified access profile"
	::= { apmPaStatEntry 187 } 

apmPaStatVaAgentTotalSessVars OBJECT-TYPE 
	SYNTAX Counter64
	MAX-ACCESS read-only
	STATUS	 deprecated
	DESCRIPTION
		"Deprecated!
	    The total session variables created by the Variable Assignment agent in the specified access profile"
	::= { apmPaStatEntry 188 } 

apmPaStatIeAgentTotalInstances OBJECT-TYPE 
	SYNTAX Counter64
	MAX-ACCESS read-only
	STATUS	 deprecated
	DESCRIPTION
		"Deprecated!
	    The total instances of the iRule Event agent in the specified access profile"
	::= { apmPaStatEntry 189 } 

apmPaStatIeAgentTotalUsages OBJECT-TYPE 
	SYNTAX Counter64
	MAX-ACCESS read-only
	STATUS	 deprecated
	DESCRIPTION
		"Deprecated!
	    The total usages of iRule Event agent in the specified access profile"
	::= { apmPaStatEntry 190 } 

apmPaStatIeAgentTotalSuccesses OBJECT-TYPE 
	SYNTAX Counter64
	MAX-ACCESS read-only
	STATUS	 deprecated
	DESCRIPTION
		"Deprecated!
	    The total success conditions created/reached by the iRule Event agent in the specified access profile"
	::= { apmPaStatEntry 191 } 

apmPaStatIeAgentTotalFailures OBJECT-TYPE 
	SYNTAX Counter64
	MAX-ACCESS read-only
	STATUS	 deprecated
	DESCRIPTION
		"Deprecated!
	    The total failure conditions created/reached by the iRule Event agent in the specified access profile"
	::= { apmPaStatEntry 192 } 

apmPaStatIeAgentTotalErrors OBJECT-TYPE 
	SYNTAX Counter64
	MAX-ACCESS read-only
	STATUS	 deprecated
	DESCRIPTION
		"Deprecated!
	    The total error conditions created/reached by the iRule Event agent in the specified access profile"
	::= { apmPaStatEntry 193 } 

apmPaStatIeAgentTotalSessVars OBJECT-TYPE 
	SYNTAX Counter64
	MAX-ACCESS read-only
	STATUS	 deprecated
	DESCRIPTION
		"Deprecated!
	    The total session variables created by the iRule Event agent in the specified access profile"
	::= { apmPaStatEntry 194 } 

apmPaStatLoggingAgentTotalInstances OBJECT-TYPE 
	SYNTAX Counter64
	MAX-ACCESS read-only
	STATUS	 deprecated
	DESCRIPTION
		"Deprecated!
	    The total instances of the Logging Agent in the specified access profile"
	::= { apmPaStatEntry 195 } 

apmPaStatLoggingAgentTotalUsages OBJECT-TYPE 
	SYNTAX Counter64
	MAX-ACCESS read-only
	STATUS	 deprecated
	DESCRIPTION
		"Deprecated!
	    The total usages of Logging Agent in the specified access profile"
	::= { apmPaStatEntry 196 } 

apmPaStatLoggingAgentTotalSuccesses OBJECT-TYPE 
	SYNTAX Counter64
	MAX-ACCESS read-only
	STATUS	 deprecated
	DESCRIPTION
		"Deprecated!
	    The total success conditions created/reached by the Logging Agent in the specified access profile"
	::= { apmPaStatEntry 197 } 

apmPaStatLoggingAgentTotalFailures OBJECT-TYPE 
	SYNTAX Counter64
	MAX-ACCESS read-only
	STATUS	 deprecated
	DESCRIPTION
		"Deprecated!
	    The total failure conditions created/reached by the Logging Agent in the specified access profile"
	::= { apmPaStatEntry 198 } 

apmPaStatLoggingAgentTotalErrors OBJECT-TYPE 
	SYNTAX Counter64
	MAX-ACCESS read-only
	STATUS	 deprecated
	DESCRIPTION
		"Deprecated!
	    The total error conditions created/reached by the Logging Agent in the specified access profile"
	::= { apmPaStatEntry 199 } 

apmPaStatLoggingAgentTotalSessVars OBJECT-TYPE 
	SYNTAX Counter64
	MAX-ACCESS read-only
	STATUS	 deprecated
	DESCRIPTION
		"Deprecated!
	    The total session variables created by the Logging Agent in the specified access profile"
	::= { apmPaStatEntry 200 } 

apmPaStatDecnBoxAgentTotalInstances OBJECT-TYPE 
	SYNTAX Counter64
	MAX-ACCESS read-only
	STATUS	 deprecated
	DESCRIPTION
		"Deprecated!
	    The total instances of the Decision Box Agent in the specified access profile"
	::= { apmPaStatEntry 201 } 

apmPaStatDecnBoxAgentTotalUsages OBJECT-TYPE 
	SYNTAX Counter64
	MAX-ACCESS read-only
	STATUS	 deprecated
	DESCRIPTION
		"Deprecated!
	    The total usages of Decision Box Agent in the specified access profile"
	::= { apmPaStatEntry 202 } 

apmPaStatDecnBoxAgentTotalSuccesses OBJECT-TYPE 
	SYNTAX Counter64
	MAX-ACCESS read-only
	STATUS	 deprecated
	DESCRIPTION
		"Deprecated!
	    The total success conditions created/reached by the Decision Box Agent in the specified access profile"
	::= { apmPaStatEntry 203 } 

apmPaStatDecnBoxAgentTotalFailures OBJECT-TYPE 
	SYNTAX Counter64
	MAX-ACCESS read-only
	STATUS	 deprecated
	DESCRIPTION
		"Deprecated!
	    The total failure conditions created/reached by the Decision Box Agent in the specified access profile"
	::= { apmPaStatEntry 204 } 

apmPaStatDecnBoxAgentTotalErrors OBJECT-TYPE 
	SYNTAX Counter64
	MAX-ACCESS read-only
	STATUS	 deprecated
	DESCRIPTION
		"Deprecated!
	    The total error conditions created/reached by the Decision Box Agent in the specified access profile"
	::= { apmPaStatEntry 205 } 

apmPaStatDecnBoxAgentTotalSessVars OBJECT-TYPE 
	SYNTAX Counter64
	MAX-ACCESS read-only
	STATUS	 deprecated
	DESCRIPTION
		"Deprecated!
	    The total session variables created by the Decision Box Agent in the specified access profile"
	::= { apmPaStatEntry 206 } 

apmPaStatMesgBoxAgentTotalInstances OBJECT-TYPE 
	SYNTAX Counter64
	MAX-ACCESS read-only
	STATUS	 deprecated
	DESCRIPTION
		"Deprecated!
	    The total instances of the Message Box Agent in the specified access profile"
	::= { apmPaStatEntry 207 } 

apmPaStatMesgBoxAgentTotalUsages OBJECT-TYPE 
	SYNTAX Counter64
	MAX-ACCESS read-only
	STATUS	 deprecated
	DESCRIPTION
		"Deprecated!
	    The total usages of Message Box Agent in the specified access profile"
	::= { apmPaStatEntry 208 } 

apmPaStatMesgBoxAgentTotalSuccesses OBJECT-TYPE 
	SYNTAX Counter64
	MAX-ACCESS read-only
	STATUS	 deprecated
	DESCRIPTION
		"Deprecated!
	    The total success conditions created/reached by the Message Box Agent in the specified access profile"
	::= { apmPaStatEntry 209 } 

apmPaStatMesgBoxAgentTotalFailures OBJECT-TYPE 
	SYNTAX Counter64
	MAX-ACCESS read-only
	STATUS	 deprecated
	DESCRIPTION
		"Deprecated!
	    The total failure conditions created/reached by the Message Box Agent in the specified access profile"
	::= { apmPaStatEntry 210 } 

apmPaStatMesgBoxAgentTotalErrors OBJECT-TYPE 
	SYNTAX Counter64
	MAX-ACCESS read-only
	STATUS	 deprecated
	DESCRIPTION
		"Deprecated!
	    The total error conditions created/reached by the Message Box Agent in the specified access profile"
	::= { apmPaStatEntry 211 } 

apmPaStatMesgBoxAgentTotalSessVars OBJECT-TYPE 
	SYNTAX Counter64
	MAX-ACCESS read-only
	STATUS	 deprecated
	DESCRIPTION
		"Deprecated!
	    The total session variables created by the Message Box Agent in the specified access profile"
	::= { apmPaStatEntry 212 } 

apmPaStatApdNoResultErrors OBJECT-TYPE 
	SYNTAX Counter64
	MAX-ACCESS read-only
	STATUS	 deprecated
	DESCRIPTION
		"Deprecated!
	    The total responses received without a result by APD from the client in the specified access profile"
	::= { apmPaStatEntry 213 } 

apmPaStatApdNoSessionErrors OBJECT-TYPE 
	SYNTAX Counter64
	MAX-ACCESS read-only
	STATUS	 deprecated
	DESCRIPTION
		"Deprecated!
	    The total responses received without a valid session by APD from the client in the specified access profile"
	::= { apmPaStatEntry 214 } 

apmPaStatApdNoDeviceInfoErrors OBJECT-TYPE 
	SYNTAX Counter64
	MAX-ACCESS read-only
	STATUS	 deprecated
	DESCRIPTION
		"Deprecated!
	    The total responses received without device info by APD from the client in the specified access profile"
	::= { apmPaStatEntry 215 } 

apmPaStatApdNoTokenErrors OBJECT-TYPE 
	SYNTAX Counter64
	MAX-ACCESS read-only
	STATUS	 deprecated
	DESCRIPTION
		"Deprecated!
	    The total responses received without a token by APD from the client in the specified access profile"
	::= { apmPaStatEntry 216 } 

apmPaStatApdNoSigErrors OBJECT-TYPE 
	SYNTAX Counter64
	MAX-ACCESS read-only
	STATUS	 deprecated
	DESCRIPTION
		"Deprecated!
	    The total responses received without a signature by APD from the client in the specified access profile"
	::= { apmPaStatEntry 217 } 

apmPaStatApdTotalMismatchErrors OBJECT-TYPE 
	SYNTAX Counter64
	MAX-ACCESS read-only
	STATUS	 deprecated
	DESCRIPTION
		"Deprecated!
	    The total responses received with client data mismatch by APD from the client in the specified access profile"
	::= { apmPaStatEntry 218 } 

apmPaStatApdInvalidSigErrors OBJECT-TYPE 
	SYNTAX Counter64
	MAX-ACCESS read-only
	STATUS	 deprecated
	DESCRIPTION
		"Deprecated!
	    The total responses received with invalid client data signature by APD from the client in the specified access profile"
	::= { apmPaStatEntry 219 } 

apmPaStatApdMcPipelineInitErrors OBJECT-TYPE 
	SYNTAX Counter64
	MAX-ACCESS read-only
	STATUS	 deprecated
	DESCRIPTION
		"Deprecated!
	    The total pipeline initialization errors caused by memcached in APD"
	::= { apmPaStatEntry 220 } 

apmPaStatApdMcSetSessVarErrors OBJECT-TYPE 
	SYNTAX Counter64
	MAX-ACCESS read-only
	STATUS	 deprecated
	DESCRIPTION
		"Deprecated!
	    The total session var set errors caused by memcached in APD"
	::= { apmPaStatEntry 221 } 

apmPaStatApdMcPipelineCloseErrors OBJECT-TYPE 
	SYNTAX Counter64
	MAX-ACCESS read-only
	STATUS	 deprecated
	DESCRIPTION
		"Deprecated!
	    The total pipeline close errors caused by memcached in APD"
	::= { apmPaStatEntry 222 } 

apmPaStatApdApResultErrors OBJECT-TYPE 
	SYNTAX Counter64
	MAX-ACCESS read-only
	STATUS	 deprecated
	DESCRIPTION
		"Deprecated!
	    The total access policy result errors in APD"
	::= { apmPaStatEntry 223 } 

apmPaStatApdApInternalErrors OBJECT-TYPE 
	SYNTAX Counter64
	MAX-ACCESS read-only
	STATUS	 deprecated
	DESCRIPTION
		"Deprecated!
	    The total access policy internal errors in APD"
	::= { apmPaStatEntry 224 } 

apmPaStatAllowedRequests OBJECT-TYPE 
	SYNTAX Counter64
	MAX-ACCESS read-only
	STATUS current
	DESCRIPTION
		"The total allowed requests in the specified access profile"
	::= { apmPaStatEntry 225 } 

apmPaStatDeniedRequests OBJECT-TYPE 
	SYNTAX Counter64
	MAX-ACCESS read-only
	STATUS current
	DESCRIPTION
		"The total denied requests in the specified access profile"
	::= { apmPaStatEntry 226 } 

apmPaStatVsName OBJECT-TYPE 
	SYNTAX LongDisplayString
	MAX-ACCESS read-only
	STATUS current
	DESCRIPTION
		"The name virtual server in the specified access profile"
	::= { apmPaStatEntry 227 } 

apmPaStatSessionsEvalTimedOut OBJECT-TYPE 
	SYNTAX Counter64
	MAX-ACCESS read-only
	STATUS current
	DESCRIPTION
		"The total sessions terminated due to inactivity while going through
	    access policy evaluation in the specified profile"
	::= { apmPaStatEntry 228 } 

apmPaStatSessionsEstabTimedOut OBJECT-TYPE 
	SYNTAX Counter64
	MAX-ACCESS read-only
	STATUS current
	DESCRIPTION
		"The total sessions terminated due to inactivity after completed
	    access policy evaluation in the specified profile"
	::= { apmPaStatEntry 229 } 

--==================================================================
-- Profile_connectivity_stat
--==================================================================
apmPcStatResetStats OBJECT-TYPE 
	SYNTAX INTEGER
	MAX-ACCESS read-write
	STATUS current
	DESCRIPTION
		"The action to reset resettable statistics data in apmProfileConnectivityStat.
		 Setting this value to 1 will reset statistics data.
		 Note, some statistics data may not be reset including data that are incremental counters."
	::= { apmProfileConnectivityStat 1 } 

apmPcStatNumber OBJECT-TYPE 
	SYNTAX INTEGER
	MAX-ACCESS read-only
	STATUS current
	DESCRIPTION
		"The number of apmProfileConnectivityStat entries in the table."
	::= { apmProfileConnectivityStat 2 } 

apmPcStatTable OBJECT-TYPE
	SYNTAX SEQUENCE OF ApmPcStatEntry
	MAX-ACCESS not-accessible
	STATUS current
	DESCRIPTION
		"A table containing statistic information of connectivity profiles."
	::= { apmProfileConnectivityStat 3 } 

apmPcStatEntry OBJECT-TYPE
	SYNTAX  ApmPcStatEntry
	MAX-ACCESS not-accessible
	STATUS current
	DESCRIPTION
		"Columns in the apmPcStat Table"
	INDEX {
		apmPcStatName
	}
	::= { apmPcStatTable 1 } 

ApmPcStatEntry ::= 
	SEQUENCE {
        	apmPcStatName                                             LongDisplayString,
        	apmPcStatTotConns                                         Counter64,
        	apmPcStatCurConns                                         Counter64,
        	apmPcStatMaxConns                                         Counter64,
        	apmPcStatIngressRaw                                       Counter64,
        	apmPcStatEgressRaw                                        Counter64,
        	apmPcStatIngressCompressed                                Counter64,
        	apmPcStatEgressCompressed                                 Counter64
	}

apmPcStatName OBJECT-TYPE 
	SYNTAX LongDisplayString
	MAX-ACCESS read-only
	STATUS current
	DESCRIPTION
		"The name of a connectivity profile"
	::= { apmPcStatEntry 1 } 

apmPcStatTotConns OBJECT-TYPE 
	SYNTAX Counter64
	MAX-ACCESS read-only
	STATUS current
	DESCRIPTION
		"The total SSL/VPN connections in the system"
	::= { apmPcStatEntry 2 } 

apmPcStatCurConns OBJECT-TYPE 
	SYNTAX Counter64
	MAX-ACCESS read-only
	STATUS current
	DESCRIPTION
		"The total current SSL/VPN connections in the system"
	::= { apmPcStatEntry 3 } 

apmPcStatMaxConns OBJECT-TYPE 
	SYNTAX Counter64
	MAX-ACCESS read-only
	STATUS current
	DESCRIPTION
		"The max SSL/VPN connections in the system"
	::= { apmPcStatEntry 4 } 

apmPcStatIngressRaw OBJECT-TYPE 
	SYNTAX Counter64
	MAX-ACCESS read-only
	STATUS current
	DESCRIPTION
		"The total raw bytes received by SSL/VPN connections in the system when compression is enabled."
	::= { apmPcStatEntry 5 } 

apmPcStatEgressRaw OBJECT-TYPE 
	SYNTAX Counter64
	MAX-ACCESS read-only
	STATUS current
	DESCRIPTION
		"The total raw bytes transmitted by SSL/VPN connections in the system when compression is enabled."
	::= { apmPcStatEntry 6 } 

apmPcStatIngressCompressed OBJECT-TYPE 
	SYNTAX Counter64
	MAX-ACCESS read-only
	STATUS current
	DESCRIPTION
		"The total compressed bytes received by SSL/VPN connections in the system when compression is enabled."
	::= { apmPcStatEntry 7 } 

apmPcStatEgressCompressed OBJECT-TYPE 
	SYNTAX Counter64
	MAX-ACCESS read-only
	STATUS current
	DESCRIPTION
		"The total compressed bytes transmitted by SSL/VPN connections in the system when compression is enabled."
	::= { apmPcStatEntry 8 } 

--==================================================================
-- Profile_rewrite_stat
--==================================================================
apmPrStatResetStats OBJECT-TYPE 
	SYNTAX INTEGER
	MAX-ACCESS read-write
	STATUS current
	DESCRIPTION
		"The action to reset resettable statistics data in apmProfileRewriteStat.
		 Setting this value to 1 will reset statistics data.
		 Note, some statistics data may not be reset including data that are incremental counters."
	::= { apmProfileRewriteStat 1 } 

apmPrStatNumber OBJECT-TYPE 
	SYNTAX INTEGER
	MAX-ACCESS read-only
	STATUS current
	DESCRIPTION
		"The number of apmProfileRewriteStat entries in the table."
	::= { apmProfileRewriteStat 2 } 

apmPrStatTable OBJECT-TYPE
	SYNTAX SEQUENCE OF ApmPrStatEntry
	MAX-ACCESS not-accessible
	STATUS current
	DESCRIPTION
		"A table containing statistic information of rewrite profiles."
	::= { apmProfileRewriteStat 3 } 

apmPrStatEntry OBJECT-TYPE
	SYNTAX  ApmPrStatEntry
	MAX-ACCESS not-accessible
	STATUS current
	DESCRIPTION
		"Columns in the apmPrStat Table"
	INDEX {
		apmPrStatName
	}
	::= { apmPrStatTable 1 } 

ApmPrStatEntry ::= 
	SEQUENCE {
        	apmPrStatName                                             LongDisplayString,
        	apmPrStatClientReqBytes                                   Counter64,
        	apmPrStatClientRespBytes                                  Counter64,
        	apmPrStatServerReqBytes                                   Counter64,
        	apmPrStatServerRespBytes                                  Counter64,
        	apmPrStatClientReqs                                       Counter64,
        	apmPrStatClientResps                                      Counter64,
        	apmPrStatServerReqs                                       Counter64,
        	apmPrStatServerResps                                      Counter64
	}

apmPrStatName OBJECT-TYPE 
	SYNTAX LongDisplayString
	MAX-ACCESS read-only
	STATUS current
	DESCRIPTION
		"The name of a rewrite profile"
	::= { apmPrStatEntry 1 } 

apmPrStatClientReqBytes OBJECT-TYPE 
	SYNTAX Counter64
	MAX-ACCESS read-only
	STATUS current
	DESCRIPTION
		"The total number of bytes received from the client requests"
	::= { apmPrStatEntry 2 } 

apmPrStatClientRespBytes OBJECT-TYPE 
	SYNTAX Counter64
	MAX-ACCESS read-only
	STATUS current
	DESCRIPTION
		"The total number of bytes sent in the client responses"
	::= { apmPrStatEntry 3 } 

apmPrStatServerReqBytes OBJECT-TYPE 
	SYNTAX Counter64
	MAX-ACCESS read-only
	STATUS current
	DESCRIPTION
		"The total number of bytes sent in the server requests"
	::= { apmPrStatEntry 4 } 

apmPrStatServerRespBytes OBJECT-TYPE 
	SYNTAX Counter64
	MAX-ACCESS read-only
	STATUS current
	DESCRIPTION
		"The total number of bytes received from the server responses"
	::= { apmPrStatEntry 5 } 

apmPrStatClientReqs OBJECT-TYPE 
	SYNTAX Counter64
	MAX-ACCESS read-only
	STATUS current
	DESCRIPTION
		"The total number of the client requests received"
	::= { apmPrStatEntry 6 } 

apmPrStatClientResps OBJECT-TYPE 
	SYNTAX Counter64
	MAX-ACCESS read-only
	STATUS current
	DESCRIPTION
		"The total number of the client responses sent"
	::= { apmPrStatEntry 7 } 

apmPrStatServerReqs OBJECT-TYPE 
	SYNTAX Counter64
	MAX-ACCESS read-only
	STATUS current
	DESCRIPTION
		"The total number requests sent to the server"
	::= { apmPrStatEntry 8 } 

apmPrStatServerResps OBJECT-TYPE 
	SYNTAX Counter64
	MAX-ACCESS read-only
	STATUS current
	DESCRIPTION
		"The total number responses received from the server"
	::= { apmPrStatEntry 9 } 

--==================================================================
-- Profile_access_agent_stat
--==================================================================
apmPgStatResetStats OBJECT-TYPE 
	SYNTAX INTEGER
	MAX-ACCESS read-write
	STATUS current
	DESCRIPTION
		"The action to reset resettable statistics data in apmProfileAccessAgentStat.
		 Setting this value to 1 will reset statistics data.
		 Note, some statistics data may not be reset including data that are incremental counters."
	::= { apmProfileAccessAgentStat 1 } 

apmPgStatNumber OBJECT-TYPE 
	SYNTAX INTEGER
	MAX-ACCESS read-only
	STATUS current
	DESCRIPTION
		"The number of apmProfileAccessAgentStat entries in the table."
	::= { apmProfileAccessAgentStat 2 } 

apmPgStatTable OBJECT-TYPE
	SYNTAX SEQUENCE OF ApmPgStatEntry
	MAX-ACCESS not-accessible
	STATUS current
	DESCRIPTION
		"A table containing statistic information of agents per access profiles."
	::= { apmProfileAccessAgentStat 3 } 

apmPgStatEntry OBJECT-TYPE
	SYNTAX  ApmPgStatEntry
	MAX-ACCESS not-accessible
	STATUS current
	DESCRIPTION
		"Columns in the apmPgStat Table"
	INDEX {
		apmPgStatName,
		apmPgStatAgentName
	}
	::= { apmPgStatTable 1 } 

ApmPgStatEntry ::= 
	SEQUENCE {
        	apmPgStatName                                             LongDisplayString,
        	apmPgStatAgentName                                        LongDisplayString,
        	apmPgStatInstances                                        Counter64,
        	apmPgStatUsages                                           Counter64,
        	apmPgStatSuccesses                                        Counter64,
        	apmPgStatFailures                                         Counter64,
        	apmPgStatErrors                                           Counter64,
        	apmPgStatSessionVars                                      Counter64
	}

apmPgStatName OBJECT-TYPE 
	SYNTAX LongDisplayString
	MAX-ACCESS read-only
	STATUS current
	DESCRIPTION
		"The name of an access profile"
	::= { apmPgStatEntry 1 } 

apmPgStatAgentName OBJECT-TYPE 
	SYNTAX LongDisplayString
	MAX-ACCESS read-only
	STATUS current
	DESCRIPTION
		"The agent name in the specified access profile"
	::= { apmPgStatEntry 2 } 

apmPgStatInstances OBJECT-TYPE 
	SYNTAX Counter64
	MAX-ACCESS read-only
	STATUS current
	DESCRIPTION
		"The total instances of agent in the specified access profile"
	::= { apmPgStatEntry 3 } 

apmPgStatUsages OBJECT-TYPE 
	SYNTAX Counter64
	MAX-ACCESS read-only
	STATUS current
	DESCRIPTION
		"The total usages of agent in the specified access profile"
	::= { apmPgStatEntry 4 } 

apmPgStatSuccesses OBJECT-TYPE 
	SYNTAX Counter64
	MAX-ACCESS read-only
	STATUS current
	DESCRIPTION
		"The total number of successes for agent in the specified access profile"
	::= { apmPgStatEntry 5 } 

apmPgStatFailures OBJECT-TYPE 
	SYNTAX Counter64
	MAX-ACCESS read-only
	STATUS current
	DESCRIPTION
		"The total number of failures for agent in the specified access profile"
	::= { apmPgStatEntry 6 } 

apmPgStatErrors OBJECT-TYPE 
	SYNTAX Counter64
	MAX-ACCESS read-only
	STATUS current
	DESCRIPTION
		"The total number of errors for agent in the specified access profile"
	::= { apmPgStatEntry 7 } 

apmPgStatSessionVars OBJECT-TYPE 
	SYNTAX Counter64
	MAX-ACCESS read-only
	STATUS current
	DESCRIPTION
		"The total number of session variables for agent in the specified access profile"
	::= { apmPgStatEntry 8 } 

--==================================================================
-- Profile_access_misc_stat
--==================================================================
apmPmStatResetStats OBJECT-TYPE 
	SYNTAX INTEGER
	MAX-ACCESS read-write
	STATUS current
	DESCRIPTION
		"The action to reset resettable statistics data in apmProfileAccessMiscStat.
		 Setting this value to 1 will reset statistics data.
		 Note, some statistics data may not be reset including data that are incremental counters."
	::= { apmProfileAccessMiscStat 1 } 

apmPmStatNumber OBJECT-TYPE 
	SYNTAX INTEGER
	MAX-ACCESS read-only
	STATUS current
	DESCRIPTION
		"The number of apmProfileAccessMiscStat entries in the table."
	::= { apmProfileAccessMiscStat 2 } 

apmPmStatTable OBJECT-TYPE
	SYNTAX SEQUENCE OF ApmPmStatEntry
	MAX-ACCESS not-accessible
	STATUS current
	DESCRIPTION
		"A table containing miscellaneous statistic information for access profiles."
	::= { apmProfileAccessMiscStat 3 } 

apmPmStatEntry OBJECT-TYPE
	SYNTAX  ApmPmStatEntry
	MAX-ACCESS not-accessible
	STATUS current
	DESCRIPTION
		"Columns in the apmPmStat Table"
	INDEX {
		apmPmStatName
	}
	::= { apmPmStatTable 1 } 

ApmPmStatEntry ::= 
	SEQUENCE {
        	apmPmStatName                                             LongDisplayString,
        	apmPmStatConfigSyncState                                  Counter64,
        	apmPmStatInspResultError                                  Counter64,
        	apmPmStatInspSessionError                                 Counter64,
        	apmPmStatInspDeviceInfoError                              Counter64,
        	apmPmStatInspTokenError                                   Counter64,
        	apmPmStatInspSignatureError                               Counter64,
        	apmPmStatInspDataMsmtchError                              Counter64,
        	apmPmStatInspClientSignError                              Counter64,
        	apmPmStatMemInitError                                     Counter64,
        	apmPmStatMemSessionVarError                               Counter64,
        	apmPmStatMemCloseError                                    Counter64,
        	apmPmStatResultError                                      Counter64,
        	apmPmStatInternalError                                    Counter64
	}

apmPmStatName OBJECT-TYPE 
	SYNTAX LongDisplayString
	MAX-ACCESS read-only
	STATUS current
	DESCRIPTION
		"The name of an access profile"
	::= { apmPmStatEntry 1 } 

apmPmStatConfigSyncState OBJECT-TYPE 
	SYNTAX Counter64
	MAX-ACCESS read-only
	STATUS current
	DESCRIPTION
		"The state of config sync operation"
	::= { apmPmStatEntry 2 } 

apmPmStatInspResultError OBJECT-TYPE 
	SYNTAX Counter64
	MAX-ACCESS read-only
	STATUS current
	DESCRIPTION
		"The total number of errors inspection host no result in the specified access profile"
	::= { apmPmStatEntry 3 } 

apmPmStatInspSessionError OBJECT-TYPE 
	SYNTAX Counter64
	MAX-ACCESS read-only
	STATUS current
	DESCRIPTION
		"The total number of errors inspection host no session in the specified access profile"
	::= { apmPmStatEntry 4 } 

apmPmStatInspDeviceInfoError OBJECT-TYPE 
	SYNTAX Counter64
	MAX-ACCESS read-only
	STATUS current
	DESCRIPTION
		"The total number of errors inspection host no device info in the specified access profile"
	::= { apmPmStatEntry 5 } 

apmPmStatInspTokenError OBJECT-TYPE 
	SYNTAX Counter64
	MAX-ACCESS read-only
	STATUS current
	DESCRIPTION
		"The total number of errors inspection host no token in the specified access profile"
	::= { apmPmStatEntry 6 } 

apmPmStatInspSignatureError OBJECT-TYPE 
	SYNTAX Counter64
	MAX-ACCESS read-only
	STATUS current
	DESCRIPTION
		"The total number of errors inspection host no signature in the specified access profile"
	::= { apmPmStatEntry 7 } 

apmPmStatInspDataMsmtchError OBJECT-TYPE 
	SYNTAX Counter64
	MAX-ACCESS read-only
	STATUS current
	DESCRIPTION
		"The total number of errors inspection host client data mismatch in the specified access profile"
	::= { apmPmStatEntry 8 } 

apmPmStatInspClientSignError OBJECT-TYPE 
	SYNTAX Counter64
	MAX-ACCESS read-only
	STATUS current
	DESCRIPTION
		"The total number of errors invalid client data signature in the specified access profile"
	::= { apmPmStatEntry 9 } 

apmPmStatMemInitError OBJECT-TYPE 
	SYNTAX Counter64
	MAX-ACCESS read-only
	STATUS current
	DESCRIPTION
		"The total number of errors memory cached pipeline in the specified access profile"
	::= { apmPmStatEntry 10 } 

apmPmStatMemSessionVarError OBJECT-TYPE 
	SYNTAX Counter64
	MAX-ACCESS read-only
	STATUS current
	DESCRIPTION
		"The total number of errors memory set session variable in the specified access profile"
	::= { apmPmStatEntry 11 } 

apmPmStatMemCloseError OBJECT-TYPE 
	SYNTAX Counter64
	MAX-ACCESS read-only
	STATUS current
	DESCRIPTION
		"The total number of errors memory finish pipeline failed in the specified access profile"
	::= { apmPmStatEntry 12 } 

apmPmStatResultError OBJECT-TYPE 
	SYNTAX Counter64
	MAX-ACCESS read-only
	STATUS current
	DESCRIPTION
		"The total number of result errors in the specified access profile"
	::= { apmPmStatEntry 13 } 

apmPmStatInternalError OBJECT-TYPE 
	SYNTAX Counter64
	MAX-ACCESS read-only
	STATUS current
	DESCRIPTION
		"The total number of internal errors in the specified access profile"
	::= { apmPmStatEntry 14 } 

--==================================================================
-- Access_stat
--==================================================================
apmAccessStatResetStats OBJECT-TYPE 
	SYNTAX INTEGER
	MAX-ACCESS read-write
	STATUS current
	DESCRIPTION
		"The action to reset resettable statistics data in apmAccessStat.
		 Setting this value to 1 will reset statistics data.
		 Note, some statistics data may not be reset including data that are incremental counters."
	::= { apmAccessStat 1 } 

apmAccessStatTotalSessions OBJECT-TYPE 
	SYNTAX Gauge
	MAX-ACCESS read-only
	STATUS current
	DESCRIPTION
		"The total sessions created in the system"
	::= { apmAccessStat 2 } 

apmAccessStatCurrentActiveSessions OBJECT-TYPE 
	SYNTAX Gauge
	MAX-ACCESS read-only
	STATUS current
	DESCRIPTION
		"The total active user sessions in the system"
	::= { apmAccessStat 3 } 

apmAccessStatCurrentPendingSessions OBJECT-TYPE 
	SYNTAX Counter64
	MAX-ACCESS read-only
	STATUS current
	DESCRIPTION
		"The total user sessions going through access policy evaluation in the system"
	::= { apmAccessStat 4 } 

apmAccessStatCurrentEndedSessions OBJECT-TYPE 
	SYNTAX Counter64
	MAX-ACCESS read-only
	STATUS current
	DESCRIPTION
		"The total user sessions completed access policy evaluation in the system"
	::= { apmAccessStat 5 } 

apmAccessStatUserLoggedoutSessions OBJECT-TYPE 
	SYNTAX Counter64
	MAX-ACCESS read-only
	STATUS current
	DESCRIPTION
		"The total sessions logged out by user in the system"
	::= { apmAccessStat 6 } 

apmAccessStatAdminTerminatedSessions OBJECT-TYPE 
	SYNTAX Counter64
	MAX-ACCESS read-only
	STATUS current
	DESCRIPTION
		"The total sessions terminated by admin in the system"
	::= { apmAccessStat 7 } 

apmAccessStatMiscTerminatedSessions OBJECT-TYPE 
	SYNTAX Counter64
	MAX-ACCESS read-only
	STATUS current
	DESCRIPTION
		"The total sessions terminated by internal errors/conditions in the system"
	::= { apmAccessStat 8 } 

apmAccessStatResultAllow OBJECT-TYPE 
	SYNTAX Counter64
	MAX-ACCESS read-only
	STATUS current
	DESCRIPTION
		"The total sessions resulted allow ending in the system"
	::= { apmAccessStat 9 } 

apmAccessStatResultDeny OBJECT-TYPE 
	SYNTAX Counter64
	MAX-ACCESS read-only
	STATUS current
	DESCRIPTION
		"The total sessions resulted deny ending in the system"
	::= { apmAccessStat 10 } 

apmAccessStatResultRedirect OBJECT-TYPE 
	SYNTAX Counter64
	MAX-ACCESS read-only
	STATUS current
	DESCRIPTION
		"The total sessions redirected to the configured URI after closing the session in the system"
	::= { apmAccessStat 11 } 

apmAccessStatResultRedirectWithSession OBJECT-TYPE 
	SYNTAX Counter64
	MAX-ACCESS read-only
	STATUS current
	DESCRIPTION
		"The total sessions redirected to the configured URI without closing the session in the system"
	::= { apmAccessStat 12 } 

apmAccessStatSessionsEvalTimedOut OBJECT-TYPE 
	SYNTAX Counter64
	MAX-ACCESS read-only
	STATUS current
	DESCRIPTION
		"The total sessions terminated due to inactivity while going through access
	    policy evaluation in the system"
	::= { apmAccessStat 13 } 

apmAccessStatSessionsEstabTimedOut OBJECT-TYPE 
	SYNTAX Counter64
	MAX-ACCESS read-only
	STATUS current
	DESCRIPTION
		"The total sessions terminated due to inactivity after completed access
	    policy evaluation in the system"
	::= { apmAccessStat 14 } 

--==================================================================
-- Global_connectivity_stat
--==================================================================
apmGlobalConnectivityStatResetStats OBJECT-TYPE 
	SYNTAX INTEGER
	MAX-ACCESS read-write
	STATUS current
	DESCRIPTION
		"The action to reset resettable statistics data in apmGlobalConnectivityStat.
		 Setting this value to 1 will reset statistics data.
		 Note, some statistics data may not be reset including data that are incremental counters."
	::= { apmGlobalConnectivityStat 1 } 

apmGlobalConnectivityStatTotConns OBJECT-TYPE 
	SYNTAX Counter64
	MAX-ACCESS read-only
	STATUS current
	DESCRIPTION
		"The total connectivity sessions in the system"
	::= { apmGlobalConnectivityStat 2 } 

apmGlobalConnectivityStatCurConns OBJECT-TYPE 
	SYNTAX Gauge
	MAX-ACCESS read-only
	STATUS current
	DESCRIPTION
		"The current connectivity sessions in the system"
	::= { apmGlobalConnectivityStat 3 } 

apmGlobalConnectivityStatMaxConns OBJECT-TYPE 
	SYNTAX Counter64
	MAX-ACCESS read-only
	STATUS current
	DESCRIPTION
		"The max connectivity sessions in the system"
	::= { apmGlobalConnectivityStat 4 } 

apmGlobalConnectivityStatIngressRaw OBJECT-TYPE 
	SYNTAX Counter64
	MAX-ACCESS read-only
	STATUS current
	DESCRIPTION
		"The total raw bytes received by connectivity sessions in the system"
	::= { apmGlobalConnectivityStat 5 } 

apmGlobalConnectivityStatEgressRaw OBJECT-TYPE 
	SYNTAX Counter64
	MAX-ACCESS read-only
	STATUS current
	DESCRIPTION
		"The total raw bytes transmitted by connectivity sessions in the system"
	::= { apmGlobalConnectivityStat 6 } 

apmGlobalConnectivityStatIngressCompressed OBJECT-TYPE 
	SYNTAX Counter64
	MAX-ACCESS read-only
	STATUS current
	DESCRIPTION
		"The total compressed bytes received by connectivity sessions in the system"
	::= { apmGlobalConnectivityStat 7 } 

apmGlobalConnectivityStatEgressCompressed OBJECT-TYPE 
	SYNTAX Counter64
	MAX-ACCESS read-only
	STATUS current
	DESCRIPTION
		"The total compressed bytes transmitted by connectivity sessions in the system"
	::= { apmGlobalConnectivityStat 8 } 

--==================================================================
-- Global_rewrite_stat
--==================================================================
apmGlobalRewriteStatResetStats OBJECT-TYPE 
	SYNTAX INTEGER
	MAX-ACCESS read-write
	STATUS current
	DESCRIPTION
		"The action to reset resettable statistics data in apmGlobalRewriteStat.
		 Setting this value to 1 will reset statistics data.
		 Note, some statistics data may not be reset including data that are incremental counters."
	::= { apmGlobalRewriteStat 1 } 

apmGlobalRewriteStatClientReqBytes OBJECT-TYPE 
	SYNTAX Counter64
	MAX-ACCESS read-only
	STATUS current
	DESCRIPTION
		"The total number of bytes received from the client requests"
	::= { apmGlobalRewriteStat 2 } 

apmGlobalRewriteStatClientRespBytes OBJECT-TYPE 
	SYNTAX Counter64
	MAX-ACCESS read-only
	STATUS current
	DESCRIPTION
		"The total number of bytes sent in the client responses"
	::= { apmGlobalRewriteStat 3 } 

apmGlobalRewriteStatServerReqBytes OBJECT-TYPE 
	SYNTAX Counter64
	MAX-ACCESS read-only
	STATUS current
	DESCRIPTION
		"The total number of bytes sent in the server requests"
	::= { apmGlobalRewriteStat 4 } 

apmGlobalRewriteStatServerRespBytes OBJECT-TYPE 
	SYNTAX Counter64
	MAX-ACCESS read-only
	STATUS current
	DESCRIPTION
		"The total number of bytes received from the server responses"
	::= { apmGlobalRewriteStat 5 } 

apmGlobalRewriteStatClientReqs OBJECT-TYPE 
	SYNTAX Counter64
	MAX-ACCESS read-only
	STATUS current
	DESCRIPTION
		"The total number of the client requests received"
	::= { apmGlobalRewriteStat 6 } 

apmGlobalRewriteStatClientResps OBJECT-TYPE 
	SYNTAX Counter64
	MAX-ACCESS read-only
	STATUS current
	DESCRIPTION
		"The total number of the client responses sent"
	::= { apmGlobalRewriteStat 7 } 

apmGlobalRewriteStatServerReqs OBJECT-TYPE 
	SYNTAX Counter64
	MAX-ACCESS read-only
	STATUS current
	DESCRIPTION
		"The total number requests sent to the server"
	::= { apmGlobalRewriteStat 8 } 

apmGlobalRewriteStatServerResps OBJECT-TYPE 
	SYNTAX Counter64
	MAX-ACCESS read-only
	STATUS current
	DESCRIPTION
		"The total number responses received from the server"
	::= { apmGlobalRewriteStat 9 } 

--==================================================================
-- Leasepool_stat
--==================================================================
apmLeasepoolStatResetStats OBJECT-TYPE 
	SYNTAX INTEGER
	MAX-ACCESS read-write
	STATUS current
	DESCRIPTION
		"The action to reset resettable statistics data in apmLeasepoolStat.
		 Setting this value to 1 will reset statistics data.
		 Note, some statistics data may not be reset including data that are incremental counters."
	::= { apmLeasepoolStat 1 } 

apmLeasepoolStatNumber OBJECT-TYPE 
	SYNTAX INTEGER
	MAX-ACCESS read-only
	STATUS current
	DESCRIPTION
		"The number of apmLeasepoolStat entries in the table."
	::= { apmLeasepoolStat 2 } 

apmLeasepoolStatTable OBJECT-TYPE
	SYNTAX SEQUENCE OF ApmLeasepoolStatEntry
	MAX-ACCESS not-accessible
	STATUS current
	DESCRIPTION
		"A table containing statistic information of ipv4 leasepools."
	::= { apmLeasepoolStat 3 } 

apmLeasepoolStatEntry OBJECT-TYPE
	SYNTAX  ApmLeasepoolStatEntry
	MAX-ACCESS not-accessible
	STATUS current
	DESCRIPTION
		"Columns in the apmLeasepoolStat Table"
	INDEX {
		apmLeasepoolStatName
	}
	::= { apmLeasepoolStatTable 1 } 

ApmLeasepoolStatEntry ::= 
	SEQUENCE {
        	apmLeasepoolStatName                                      LongDisplayString,
        	apmLeasepoolStatCurMembers                                Gauge,
        	apmLeasepoolStatCurAssigned                               Gauge,
        	apmLeasepoolStatCurFree                                   Gauge,
        	apmLeasepoolStatMaxAssigned                               Gauge,
        	apmLeasepoolStatTotPickRequests                           Counter64,
        	apmLeasepoolStatTotPickFailure                            Counter64,
        	apmLeasepoolStatTotReserveRequests                        Counter64,
        	apmLeasepoolStatTotReserveFailure                         Counter64,
        	apmLeasepoolStatTotReleaseRequests                        Counter64,
        	apmLeasepoolStatTotReleaseFailure                         Counter64
	}

apmLeasepoolStatName OBJECT-TYPE 
	SYNTAX LongDisplayString
	MAX-ACCESS read-only
	STATUS current
	DESCRIPTION
		"The name of a leasepool"
	::= { apmLeasepoolStatEntry 1 } 

apmLeasepoolStatCurMembers OBJECT-TYPE 
	SYNTAX Gauge
	MAX-ACCESS read-only
	STATUS current
	DESCRIPTION
		"The current number of IPv4 addresses in the leasepool"
	::= { apmLeasepoolStatEntry 2 } 

apmLeasepoolStatCurAssigned OBJECT-TYPE 
	SYNTAX Gauge
	MAX-ACCESS read-only
	STATUS current
	DESCRIPTION
		"The number of IPv4 addresses currently assigned to user sessions"
	::= { apmLeasepoolStatEntry 3 } 

apmLeasepoolStatCurFree OBJECT-TYPE 
	SYNTAX Gauge
	MAX-ACCESS read-only
	STATUS current
	DESCRIPTION
		"The number of available/free IPv4 addresses in the leasepool"
	::= { apmLeasepoolStatEntry 4 } 

apmLeasepoolStatMaxAssigned OBJECT-TYPE 
	SYNTAX Gauge
	MAX-ACCESS read-only
	STATUS current
	DESCRIPTION
		"The max number of IPv4 addresses assigned at any single time in the leasepool since last stats reset"
	::= { apmLeasepoolStatEntry 5 } 

apmLeasepoolStatTotPickRequests OBJECT-TYPE 
	SYNTAX Counter64
	MAX-ACCESS read-only
	STATUS current
	DESCRIPTION
		"The total number of requests for IPv4 addresses from active unit in HA pair"
	::= { apmLeasepoolStatEntry 6 } 

apmLeasepoolStatTotPickFailure OBJECT-TYPE 
	SYNTAX Counter64
	MAX-ACCESS read-only
	STATUS current
	DESCRIPTION
		"The total number of failures to assign an IPv4 address"
	::= { apmLeasepoolStatEntry 7 } 

apmLeasepoolStatTotReserveRequests OBJECT-TYPE 
	SYNTAX Counter64
	MAX-ACCESS read-only
	STATUS current
	DESCRIPTION
		"The total number of requests for specific IPv4 address from standby unit in HA pair"
	::= { apmLeasepoolStatEntry 8 } 

apmLeasepoolStatTotReserveFailure OBJECT-TYPE 
	SYNTAX Counter64
	MAX-ACCESS read-only
	STATUS current
	DESCRIPTION
		"The total number of failures to reserve a specific IPv4 address"
	::= { apmLeasepoolStatEntry 9 } 

apmLeasepoolStatTotReleaseRequests OBJECT-TYPE 
	SYNTAX Counter64
	MAX-ACCESS read-only
	STATUS current
	DESCRIPTION
		"The total number of requests to release IPv4 address for either active or standby"
	::= { apmLeasepoolStatEntry 10 } 

apmLeasepoolStatTotReleaseFailure OBJECT-TYPE 
	SYNTAX Counter64
	MAX-ACCESS read-only
	STATUS current
	DESCRIPTION
		"The total number of failures to release IP address"
	::= { apmLeasepoolStatEntry 11 } 

--==================================================================
-- Acl_stat
--==================================================================
apmAclStatResetStats OBJECT-TYPE 
	SYNTAX INTEGER
	MAX-ACCESS read-write
	STATUS current
	DESCRIPTION
		"The action to reset resettable statistics data in apmAclStat.
		 Setting this value to 1 will reset statistics data.
		 Note, some statistics data may not be reset including data that are incremental counters."
	::= { apmAclStat 1 } 

apmAclStatNumber OBJECT-TYPE 
	SYNTAX INTEGER
	MAX-ACCESS read-only
	STATUS current
	DESCRIPTION
		"The number of apmAclStat entries in the table."
	::= { apmAclStat 2 } 

apmAclStatTable OBJECT-TYPE
	SYNTAX SEQUENCE OF ApmAclStatEntry
	MAX-ACCESS not-accessible
	STATUS current
	DESCRIPTION
		"A table containing statistic information of Acls."
	::= { apmAclStat 3 } 

apmAclStatEntry OBJECT-TYPE
	SYNTAX  ApmAclStatEntry
	MAX-ACCESS not-accessible
	STATUS current
	DESCRIPTION
		"Columns in the apmAclStat Table"
	INDEX {
		apmAclStatName
	}
	::= { apmAclStatTable 1 } 

ApmAclStatEntry ::= 
	SEQUENCE {
        	apmAclStatName                                            LongDisplayString,
        	apmAclStatActionAllow                                     Counter64,
        	apmAclStatActionContinue                                  Counter64,
        	apmAclStatActionDiscard                                   Counter64,
        	apmAclStatActionReject                                    Counter64
	}

apmAclStatName OBJECT-TYPE 
	SYNTAX LongDisplayString
	MAX-ACCESS read-only
	STATUS current
	DESCRIPTION
		"The name of a acl"
	::= { apmAclStatEntry 1 } 

apmAclStatActionAllow OBJECT-TYPE 
	SYNTAX Counter64
	MAX-ACCESS read-only
	STATUS current
	DESCRIPTION
		"The number of times allow action executed"
	::= { apmAclStatEntry 2 } 

apmAclStatActionContinue OBJECT-TYPE 
	SYNTAX Counter64
	MAX-ACCESS read-only
	STATUS current
	DESCRIPTION
		"The number of times continue action executed"
	::= { apmAclStatEntry 3 } 

apmAclStatActionDiscard OBJECT-TYPE 
	SYNTAX Counter64
	MAX-ACCESS read-only
	STATUS current
	DESCRIPTION
		"The number of times discard action executed"
	::= { apmAclStatEntry 4 } 

apmAclStatActionReject OBJECT-TYPE 
	SYNTAX Counter64
	MAX-ACCESS read-only
	STATUS current
	DESCRIPTION
		"The number of times reject action executed"
	::= { apmAclStatEntry 5 } 

--==================================================================
-- Global_license_stat
--==================================================================
apmGlobalLicenseStatResetStats OBJECT-TYPE 
	SYNTAX INTEGER
	MAX-ACCESS read-write
	STATUS current
	DESCRIPTION
		"The action to reset resettable statistics data in apmGlobalLicenseStat.
		 Setting this value to 1 will reset statistics data.
		 Note, some statistics data may not be reset including data that are incremental counters."
	::= { apmGlobalLicenseStat 1 } 

apmGlobalLicenseStatTotalAccessSessions OBJECT-TYPE 
	SYNTAX Gauge
	MAX-ACCESS read-only
	STATUS current
	DESCRIPTION
		"The total access session licenses in the system"
	::= { apmGlobalLicenseStat 2 } 

apmGlobalLicenseStatTotalConnectivitySessions OBJECT-TYPE 
	SYNTAX Gauge
	MAX-ACCESS read-only
	STATUS current
	DESCRIPTION
		"The total connectivity session licenses in the system"
	::= { apmGlobalLicenseStat 3 } 

apmGlobalLicenseStatTotalSwgSessions OBJECT-TYPE 
	SYNTAX Gauge
	MAX-ACCESS read-only
	STATUS current
	DESCRIPTION
		"The total secure web gateway session licenses in the system"
	::= { apmGlobalLicenseStat 4 } 

apmGlobalLicenseStatTotalSwgLimitedSessions OBJECT-TYPE 
	SYNTAX Gauge
	MAX-ACCESS read-only
	STATUS current
	DESCRIPTION
		"The total secure web gateway limited session licenses in the system"
	::= { apmGlobalLicenseStat 5 } 

--==================================================================
-- Ipv6_leasepool_stat
--==================================================================
apmIpv6LeasepoolStatResetStats OBJECT-TYPE 
	SYNTAX INTEGER
	MAX-ACCESS read-write
	STATUS current
	DESCRIPTION
		"The action to reset resettable statistics data in apmIpv6LeasepoolStat.
		 Setting this value to 1 will reset statistics data.
		 Note, some statistics data may not be reset including data that are incremental counters."
	::= { apmIpv6LeasepoolStat 1 } 

apmIpv6LeasepoolStatNumber OBJECT-TYPE 
	SYNTAX INTEGER
	MAX-ACCESS read-only
	STATUS current
	DESCRIPTION
		"The number of apmIpv6LeasepoolStat entries in the table."
	::= { apmIpv6LeasepoolStat 2 } 

apmIpv6LeasepoolStatTable OBJECT-TYPE
	SYNTAX SEQUENCE OF ApmIpv6LeasepoolStatEntry
	MAX-ACCESS not-accessible
	STATUS current
	DESCRIPTION
		"A table containing statistic information of ipv6 leasepools."
	::= { apmIpv6LeasepoolStat 3 } 

apmIpv6LeasepoolStatEntry OBJECT-TYPE
	SYNTAX  ApmIpv6LeasepoolStatEntry
	MAX-ACCESS not-accessible
	STATUS current
	DESCRIPTION
		"Columns in the apmIpv6LeasepoolStat Table"
	INDEX {
		apmIpv6LeasepoolStatName
	}
	::= { apmIpv6LeasepoolStatTable 1 } 

ApmIpv6LeasepoolStatEntry ::= 
	SEQUENCE {
        	apmIpv6LeasepoolStatName                                  LongDisplayString,
        	apmIpv6LeasepoolStatCurMembers                            Gauge,
        	apmIpv6LeasepoolStatCurAssigned                           Gauge,
        	apmIpv6LeasepoolStatCurFree                               Gauge,
        	apmIpv6LeasepoolStatMaxAssigned                           Gauge,
        	apmIpv6LeasepoolStatTotPickRequests                       Counter64,
        	apmIpv6LeasepoolStatTotPickFailure                        Counter64,
        	apmIpv6LeasepoolStatTotReserveRequests                    Counter64,
        	apmIpv6LeasepoolStatTotReserveFailure                     Counter64,
        	apmIpv6LeasepoolStatTotReleaseRequests                    Counter64,
        	apmIpv6LeasepoolStatTotReleaseFailure                     Counter64
	}

apmIpv6LeasepoolStatName OBJECT-TYPE 
	SYNTAX LongDisplayString
	MAX-ACCESS read-only
	STATUS current
	DESCRIPTION
		"The name of a leasepool"
	::= { apmIpv6LeasepoolStatEntry 1 } 

apmIpv6LeasepoolStatCurMembers OBJECT-TYPE 
	SYNTAX Gauge
	MAX-ACCESS read-only
	STATUS current
	DESCRIPTION
		"The current number of IPv6 addresses in the leasepool"
	::= { apmIpv6LeasepoolStatEntry 2 } 

apmIpv6LeasepoolStatCurAssigned OBJECT-TYPE 
	SYNTAX Gauge
	MAX-ACCESS read-only
	STATUS current
	DESCRIPTION
		"The number of IPv6 addresses currently assigned to user sessions"
	::= { apmIpv6LeasepoolStatEntry 3 } 

apmIpv6LeasepoolStatCurFree OBJECT-TYPE 
	SYNTAX Gauge
	MAX-ACCESS read-only
	STATUS current
	DESCRIPTION
		"The number of available/free IPv6 addresses in the leasepool"
	::= { apmIpv6LeasepoolStatEntry 4 } 

apmIpv6LeasepoolStatMaxAssigned OBJECT-TYPE 
	SYNTAX Gauge
	MAX-ACCESS read-only
	STATUS current
	DESCRIPTION
		"The max number of IPv6 addresses assigned at any single time in the leasepool since last stats reset"
	::= { apmIpv6LeasepoolStatEntry 5 } 

apmIpv6LeasepoolStatTotPickRequests OBJECT-TYPE 
	SYNTAX Counter64
	MAX-ACCESS read-only
	STATUS current
	DESCRIPTION
		"The total number of requests for IPv6 addresses from active unit in HA pair"
	::= { apmIpv6LeasepoolStatEntry 6 } 

apmIpv6LeasepoolStatTotPickFailure OBJECT-TYPE 
	SYNTAX Counter64
	MAX-ACCESS read-only
	STATUS current
	DESCRIPTION
		"The total number of failures to assign an IPv6 address"
	::= { apmIpv6LeasepoolStatEntry 7 } 

apmIpv6LeasepoolStatTotReserveRequests OBJECT-TYPE 
	SYNTAX Counter64
	MAX-ACCESS read-only
	STATUS current
	DESCRIPTION
		"The total number of requests for specific IPv6 address from standby unit in HA pair"
	::= { apmIpv6LeasepoolStatEntry 8 } 

apmIpv6LeasepoolStatTotReserveFailure OBJECT-TYPE 
	SYNTAX Counter64
	MAX-ACCESS read-only
	STATUS current
	DESCRIPTION
		"The total number of failures to reserve a specific IPv6 address"
	::= { apmIpv6LeasepoolStatEntry 9 } 

apmIpv6LeasepoolStatTotReleaseRequests OBJECT-TYPE 
	SYNTAX Counter64
	MAX-ACCESS read-only
	STATUS current
	DESCRIPTION
		"The total number of requests to release IPv6 address for either active or standby"
	::= { apmIpv6LeasepoolStatEntry 10 } 

apmIpv6LeasepoolStatTotReleaseFailure OBJECT-TYPE 
	SYNTAX Counter64
	MAX-ACCESS read-only
	STATUS current
	DESCRIPTION
		"The total number of failures to release IPv6 address"
	::= { apmIpv6LeasepoolStatEntry 11 } 

--================================================================
 -- Compliance and Group
--================================================================

bigipApmCompliance	MODULE-COMPLIANCE 
	STATUS current
	DESCRIPTION
		"This specifies the objects that are required to claim 
                 compliance to F5 Traffic Management System."
	MODULE
	  MANDATORY-GROUPS { bigipApmGroups } 
	::= { bigipCompliances 6 } 

bigipApmGroups  OBJECT IDENTIFIER ::= {  bigipGroups 6 }

apmPaStatGroup OBJECT-GROUP
	 OBJECTS {
		apmPaStatResetStats,
		apmPaStatNumber,
		apmPaStatName,
		apmPaStatConfigSyncState,
		apmPaStatTotalSessions,
		apmPaStatTotalEstablishedStateSessions,
		apmPaStatCurrentActiveSessions,
		apmPaStatCurrentPendingSessions,
		apmPaStatCurrentCompletedSessions,
		apmPaStatUserLoggedoutSessions,
		apmPaStatAdminTerminatedSessions,
		apmPaStatMiscTerminatedSessions,
		apmPaStatAccessPolicyResultAllow,
		apmPaStatAccessPolicyResultDeny,
		apmPaStatAccessPolicyResultRedirect,
		apmPaStatAccessPolicyResultRedirectWithSession,
		apmPaStatEndingDenyAgentTotalInstances,
		apmPaStatEndingDenyAgentTotalUsages,
		apmPaStatEndingDenyAgentTotalSuccesses,
		apmPaStatEndingDenyAgentTotalFailures,
		apmPaStatEndingDenyAgentTotalErrors,
		apmPaStatEndingDenyAgentTotalSessVars,
		apmPaStatEndingRedirectAgentTotalInstances,
		apmPaStatEndingRedirectAgentTotalUsages,
		apmPaStatEndingRedirectAgentTotalSuccesses,
		apmPaStatEndingRedirectAgentTotalFailures,
		apmPaStatEndingRedirectAgentTotalErrors,
		apmPaStatEndingRedirectAgentTotalSessVars,
		apmPaStatEndingAllowAgentTotalInstances,
		apmPaStatEndingAllowAgentTotalUsages,
		apmPaStatEndingAllowAgentTotalSuccesses,
		apmPaStatEndingAllowAgentTotalFailures,
		apmPaStatEndingAllowAgentTotalErrors,
		apmPaStatEndingAllowAgentTotalSessVars,
		apmPaStatAdAgentTotalInstances,
		apmPaStatAdAgentTotalUsages,
		apmPaStatAdAgentTotalSuccesses,
		apmPaStatAdAgentTotalFailures,
		apmPaStatAdAgentTotalErrors,
		apmPaStatAdAgentTotalSessVars,
		apmPaStatClientCertAgentTotalInstances,
		apmPaStatClientCertAgentTotalUsages,
		apmPaStatClientCertAgentTotalSuccesses,
		apmPaStatClientCertAgentTotalFailures,
		apmPaStatClientCertAgentTotalErrors,
		apmPaStatClientCertAgentTotalSessVars,
		apmPaStatHttpAgentTotalInstances,
		apmPaStatHttpAgentTotalUsages,
		apmPaStatHttpAgentTotalSuccesses,
		apmPaStatHttpAgentTotalFailures,
		apmPaStatHttpAgentTotalErrors,
		apmPaStatHttpAgentTotalSessVars,
		apmPaStatLdapAgentTotalInstances,
		apmPaStatLdapAgentTotalUsages,
		apmPaStatLdapAgentTotalSuccesses,
		apmPaStatLdapAgentTotalFailures,
		apmPaStatLdapAgentTotalErrors,
		apmPaStatLdapAgentTotalSessVars,
		apmPaStatRadiusAgentTotalInstances,
		apmPaStatRadiusAgentTotalUsages,
		apmPaStatRadiusAgentTotalSuccesses,
		apmPaStatRadiusAgentTotalFailures,
		apmPaStatRadiusAgentTotalErrors,
		apmPaStatRadiusAgentTotalSessVars,
		apmPaStatSecuridAgentTotalInstances,
		apmPaStatSecuridAgentTotalUsages,
		apmPaStatSecuridAgentTotalSuccesses,
		apmPaStatSecuridAgentTotalFailures,
		apmPaStatSecuridAgentTotalErrors,
		apmPaStatSecuridAgentTotalSessVars,
		apmPaStatRadiusAcctAgentTotalInstances,
		apmPaStatRadiusAcctAgentTotalUsages,
		apmPaStatRadiusAcctAgentTotalSuccesses,
		apmPaStatRadiusAcctAgentTotalFailures,
		apmPaStatRadiusAcctAgentTotalErrors,
		apmPaStatRadiusAcctAgentTotalSessVars,
		apmPaStatEpsLinuxFcAgentTotalInstances,
		apmPaStatEpsLinuxFcAgentTotalUsages,
		apmPaStatEpsLinuxFcAgentTotalSuccesses,
		apmPaStatEpsLinuxFcAgentTotalFailures,
		apmPaStatEpsLinuxFcAgentTotalErrors,
		apmPaStatEpsLinuxFcAgentTotalSessVars,
		apmPaStatEpsLinuxPcAgentTotalInstances,
		apmPaStatEpsLinuxPcAgentTotalUsages,
		apmPaStatEpsLinuxPcAgentTotalSuccesses,
		apmPaStatEpsLinuxPcAgentTotalFailures,
		apmPaStatEpsLinuxPcAgentTotalErrors,
		apmPaStatEpsLinuxPcAgentTotalSessVars,
		apmPaStatEpsMacFcAgentTotalInstances,
		apmPaStatEpsMacFcAgentTotalUsages,
		apmPaStatEpsMacFcAgentTotalSuccesses,
		apmPaStatEpsMacFcAgentTotalFailures,
		apmPaStatEpsMacFcAgentTotalErrors,
		apmPaStatEpsMacFcAgentTotalSessVars,
		apmPaStatEpsMacPcAgentTotalInstances,
		apmPaStatEpsMacPcAgentTotalUsages,
		apmPaStatEpsMacPcAgentTotalSuccesses,
		apmPaStatEpsMacPcAgentTotalFailures,
		apmPaStatEpsMacPcAgentTotalErrors,
		apmPaStatEpsMacPcAgentTotalSessVars,
		apmPaStatEpsWinCcAgentTotalInstances,
		apmPaStatEpsWinCcAgentTotalUsages,
		apmPaStatEpsWinCcAgentTotalSuccesses,
		apmPaStatEpsWinCcAgentTotalFailures,
		apmPaStatEpsWinCcAgentTotalErrors,
		apmPaStatEpsWinCcAgentTotalSessVars,
		apmPaStatEpsAvAgentTotalInstances,
		apmPaStatEpsAvAgentTotalUsages,
		apmPaStatEpsAvAgentTotalSuccesses,
		apmPaStatEpsAvAgentTotalFailures,
		apmPaStatEpsAvAgentTotalErrors,
		apmPaStatEpsAvAgentTotalSessVars,
		apmPaStatEpsWinOsInfoAgentTotalInstances,
		apmPaStatEpsWinOsInfoAgentTotalUsages,
		apmPaStatEpsWinOsInfoAgentTotalSuccesses,
		apmPaStatEpsWinOsInfoAgentTotalFailures,
		apmPaStatEpsWinOsInfoAgentTotalErrors,
		apmPaStatEpsWinOsInfoAgentTotalSessVars,
		apmPaStatEpsWinFcAgentTotalInstances,
		apmPaStatEpsWinFcAgentTotalUsages,
		apmPaStatEpsWinFcAgentTotalSuccesses,
		apmPaStatEpsWinFcAgentTotalFailures,
		apmPaStatEpsWinFcAgentTotalErrors,
		apmPaStatEpsWinFcAgentTotalSessVars,
		apmPaStatEpsWinMcAgentTotalInstances,
		apmPaStatEpsWinMcAgentTotalUsages,
		apmPaStatEpsWinMcAgentTotalSuccesses,
		apmPaStatEpsWinMcAgentTotalFailures,
		apmPaStatEpsWinMcAgentTotalErrors,
		apmPaStatEpsWinMcAgentTotalSessVars,
		apmPaStatEpsFwcAgentTotalInstances,
		apmPaStatEpsFwcAgentTotalUsages,
		apmPaStatEpsFwcAgentTotalSuccesses,
		apmPaStatEpsFwcAgentTotalFailures,
		apmPaStatEpsFwcAgentTotalErrors,
		apmPaStatEpsFwcAgentTotalSessVars,
		apmPaStatEpsWinPcTotalInstances,
		apmPaStatEpsWinPcTotalUsages,
		apmPaStatEpsWinPcTotalSuccesses,
		apmPaStatEpsWinPcTotalFailures,
		apmPaStatEpsWinPcTotalErrors,
		apmPaStatEpsWinPcTotalSessVars,
		apmPaStatEpsWinPwTotalInstances,
		apmPaStatEpsWinPwTotalUsages,
		apmPaStatEpsWinPwTotalSuccesses,
		apmPaStatEpsWinPwTotalFailures,
		apmPaStatEpsWinPwTotalErrors,
		apmPaStatEpsWinPwTotalSessVars,
		apmPaStatEpsWinRcAgentTotalInstances,
		apmPaStatEpsWinRcAgentTotalUsages,
		apmPaStatEpsWinRcAgentTotalSuccesses,
		apmPaStatEpsWinRcAgentTotalFailures,
		apmPaStatEpsWinRcAgentTotalErrors,
		apmPaStatEpsWinRcAgentTotalSessVars,
		apmPaStatEpsWinGpAgentTotalInstances,
		apmPaStatEpsWinGpAgentTotalUsages,
		apmPaStatEpsWinGpAgentTotalSuccesses,
		apmPaStatEpsWinGpAgentTotalFailures,
		apmPaStatEpsWinGpAgentTotalErrors,
		apmPaStatEpsWinGpAgentTotalSessVars,
		apmPaStatExternalLogonAgentTotalInstances,
		apmPaStatExternalLogonAgentTotalUsages,
		apmPaStatExternalLogonAgentTotalSuccesses,
		apmPaStatExternalLogonAgentTotalFailures,
		apmPaStatExternalLogonAgentTotalErrors,
		apmPaStatExternalLogonAgentTotalSessVars,
		apmPaStatLogonAgentTotalInstances,
		apmPaStatLogonAgentTotalUsages,
		apmPaStatLogonAgentTotalSuccesses,
		apmPaStatLogonAgentTotalFailures,
		apmPaStatLogonAgentTotalErrors,
		apmPaStatLogonAgentTotalSessVars,
		apmPaStatRaAgentTotalInstances,
		apmPaStatRaAgentTotalUsages,
		apmPaStatRaAgentTotalSuccesses,
		apmPaStatRaAgentTotalFailures,
		apmPaStatRaAgentTotalErrors,
		apmPaStatRaAgentTotalSessVars,
		apmPaStatRdsAgentTotalInstances,
		apmPaStatRdsAgentTotalUsages,
		apmPaStatRdsAgentTotalSuccesses,
		apmPaStatRdsAgentTotalFailures,
		apmPaStatRdsAgentTotalErrors,
		apmPaStatRdsAgentTotalSessVars,
		apmPaStatVaAgentTotalInstances,
		apmPaStatVaAgentTotalUsages,
		apmPaStatVaAgentTotalSuccesses,
		apmPaStatVaAgentTotalFailures,
		apmPaStatVaAgentTotalErrors,
		apmPaStatVaAgentTotalSessVars,
		apmPaStatIeAgentTotalInstances,
		apmPaStatIeAgentTotalUsages,
		apmPaStatIeAgentTotalSuccesses,
		apmPaStatIeAgentTotalFailures,
		apmPaStatIeAgentTotalErrors,
		apmPaStatIeAgentTotalSessVars,
		apmPaStatLoggingAgentTotalInstances,
		apmPaStatLoggingAgentTotalUsages,
		apmPaStatLoggingAgentTotalSuccesses,
		apmPaStatLoggingAgentTotalFailures,
		apmPaStatLoggingAgentTotalErrors,
		apmPaStatLoggingAgentTotalSessVars,
		apmPaStatDecnBoxAgentTotalInstances,
		apmPaStatDecnBoxAgentTotalUsages,
		apmPaStatDecnBoxAgentTotalSuccesses,
		apmPaStatDecnBoxAgentTotalFailures,
		apmPaStatDecnBoxAgentTotalErrors,
		apmPaStatDecnBoxAgentTotalSessVars,
		apmPaStatMesgBoxAgentTotalInstances,
		apmPaStatMesgBoxAgentTotalUsages,
		apmPaStatMesgBoxAgentTotalSuccesses,
		apmPaStatMesgBoxAgentTotalFailures,
		apmPaStatMesgBoxAgentTotalErrors,
		apmPaStatMesgBoxAgentTotalSessVars,
		apmPaStatApdNoResultErrors,
		apmPaStatApdNoSessionErrors,
		apmPaStatApdNoDeviceInfoErrors,
		apmPaStatApdNoTokenErrors,
		apmPaStatApdNoSigErrors,
		apmPaStatApdTotalMismatchErrors,
		apmPaStatApdInvalidSigErrors,
		apmPaStatApdMcPipelineInitErrors,
		apmPaStatApdMcSetSessVarErrors,
		apmPaStatApdMcPipelineCloseErrors,
		apmPaStatApdApResultErrors,
		apmPaStatApdApInternalErrors,
		apmPaStatAllowedRequests,
		apmPaStatDeniedRequests,
		apmPaStatVsName,
		apmPaStatSessionsEvalTimedOut,
		apmPaStatSessionsEstabTimedOut
	}
	STATUS	 current
	DESCRIPTION
		"A collection of objects of apmProfileAccessStat MIB."
	::= { bigipApmGroups 1 }

apmPcStatGroup OBJECT-GROUP
	 OBJECTS {
		apmPcStatResetStats,
		apmPcStatNumber,
		apmPcStatName,
		apmPcStatTotConns,
		apmPcStatCurConns,
		apmPcStatMaxConns,
		apmPcStatIngressRaw,
		apmPcStatEgressRaw,
		apmPcStatIngressCompressed,
		apmPcStatEgressCompressed
	}
	STATUS	 current
	DESCRIPTION
		"A collection of objects of apmProfileConnectivityStat MIB."
	::= { bigipApmGroups 2 }

apmPrStatGroup OBJECT-GROUP
	 OBJECTS {
		apmPrStatResetStats,
		apmPrStatNumber,
		apmPrStatName,
		apmPrStatClientReqBytes,
		apmPrStatClientRespBytes,
		apmPrStatServerReqBytes,
		apmPrStatServerRespBytes,
		apmPrStatClientReqs,
		apmPrStatClientResps,
		apmPrStatServerReqs,
		apmPrStatServerResps
	}
	STATUS	 current
	DESCRIPTION
		"A collection of objects of apmProfileRewriteStat MIB."
	::= { bigipApmGroups 3 }

apmPgStatGroup OBJECT-GROUP
	 OBJECTS {
		apmPgStatResetStats,
		apmPgStatNumber,
		apmPgStatName,
		apmPgStatAgentName,
		apmPgStatInstances,
		apmPgStatUsages,
		apmPgStatSuccesses,
		apmPgStatFailures,
		apmPgStatErrors,
		apmPgStatSessionVars
	}
	STATUS	 current
	DESCRIPTION
		"A collection of objects of apmProfileAccessAgentStat MIB."
	::= { bigipApmGroups 4 }

apmPmStatGroup OBJECT-GROUP
	 OBJECTS {
		apmPmStatResetStats,
		apmPmStatNumber,
		apmPmStatName,
		apmPmStatConfigSyncState,
		apmPmStatInspResultError,
		apmPmStatInspSessionError,
		apmPmStatInspDeviceInfoError,
		apmPmStatInspTokenError,
		apmPmStatInspSignatureError,
		apmPmStatInspDataMsmtchError,
		apmPmStatInspClientSignError,
		apmPmStatMemInitError,
		apmPmStatMemSessionVarError,
		apmPmStatMemCloseError,
		apmPmStatResultError,
		apmPmStatInternalError
	}
	STATUS	 current
	DESCRIPTION
		"A collection of objects of apmProfileAccessMiscStat MIB."
	::= { bigipApmGroups 5 }

apmAccessStatGroup OBJECT-GROUP
	 OBJECTS {
		apmAccessStatResetStats,
		apmAccessStatTotalSessions,
		apmAccessStatCurrentActiveSessions,
		apmAccessStatCurrentPendingSessions,
		apmAccessStatCurrentEndedSessions,
		apmAccessStatUserLoggedoutSessions,
		apmAccessStatAdminTerminatedSessions,
		apmAccessStatMiscTerminatedSessions,
		apmAccessStatResultAllow,
		apmAccessStatResultDeny,
		apmAccessStatResultRedirect,
		apmAccessStatResultRedirectWithSession,
		apmAccessStatSessionsEvalTimedOut,
		apmAccessStatSessionsEstabTimedOut
	}
	STATUS	 current
	DESCRIPTION
		"A collection of objects of apmAccessStat MIB."
	::= { bigipApmGroups 6 }

apmGlobalConnectivityStatGroup OBJECT-GROUP
	 OBJECTS {
		apmGlobalConnectivityStatResetStats,
		apmGlobalConnectivityStatTotConns,
		apmGlobalConnectivityStatCurConns,
		apmGlobalConnectivityStatMaxConns,
		apmGlobalConnectivityStatIngressRaw,
		apmGlobalConnectivityStatEgressRaw,
		apmGlobalConnectivityStatIngressCompressed,
		apmGlobalConnectivityStatEgressCompressed
	}
	STATUS	 current
	DESCRIPTION
		"A collection of objects of apmGlobalConnectivityStat MIB."
	::= { bigipApmGroups 7 }

apmGlobalRewriteStatGroup OBJECT-GROUP
	 OBJECTS {
		apmGlobalRewriteStatResetStats,
		apmGlobalRewriteStatClientReqBytes,
		apmGlobalRewriteStatClientRespBytes,
		apmGlobalRewriteStatServerReqBytes,
		apmGlobalRewriteStatServerRespBytes,
		apmGlobalRewriteStatClientReqs,
		apmGlobalRewriteStatClientResps,
		apmGlobalRewriteStatServerReqs,
		apmGlobalRewriteStatServerResps
	}
	STATUS	 current
	DESCRIPTION
		"A collection of objects of apmGlobalRewriteStat MIB."
	::= { bigipApmGroups 8 }

apmLeasepoolStatGroup OBJECT-GROUP
	 OBJECTS {
		apmLeasepoolStatResetStats,
		apmLeasepoolStatNumber,
		apmLeasepoolStatName,
		apmLeasepoolStatCurMembers,
		apmLeasepoolStatCurAssigned,
		apmLeasepoolStatCurFree,
		apmLeasepoolStatMaxAssigned,
		apmLeasepoolStatTotPickRequests,
		apmLeasepoolStatTotPickFailure,
		apmLeasepoolStatTotReserveRequests,
		apmLeasepoolStatTotReserveFailure,
		apmLeasepoolStatTotReleaseRequests,
		apmLeasepoolStatTotReleaseFailure
	}
	STATUS	 current
	DESCRIPTION
		"A collection of objects of apmLeasepoolStat MIB."
	::= { bigipApmGroups 9 }

apmAclStatGroup OBJECT-GROUP
	 OBJECTS {
		apmAclStatResetStats,
		apmAclStatNumber,
		apmAclStatName,
		apmAclStatActionAllow,
		apmAclStatActionContinue,
		apmAclStatActionDiscard,
		apmAclStatActionReject
	}
	STATUS	 current
	DESCRIPTION
		"A collection of objects of apmAclStat MIB."
	::= { bigipApmGroups 10 }

apmGlobalLicenseStatGroup OBJECT-GROUP
	 OBJECTS {
		apmGlobalLicenseStatResetStats,
		apmGlobalLicenseStatTotalAccessSessions,
		apmGlobalLicenseStatTotalConnectivitySessions,
		apmGlobalLicenseStatTotalSwgSessions,
		apmGlobalLicenseStatTotalSwgLimitedSessions
	}
	STATUS	 current
	DESCRIPTION
		"A collection of objects of apmGlobalLicenseStat MIB."
	::= { bigipApmGroups 11 }

apmIpv6LeasepoolStatGroup OBJECT-GROUP
	 OBJECTS {
		apmIpv6LeasepoolStatResetStats,
		apmIpv6LeasepoolStatNumber,
		apmIpv6LeasepoolStatName,
		apmIpv6LeasepoolStatCurMembers,
		apmIpv6LeasepoolStatCurAssigned,
		apmIpv6LeasepoolStatCurFree,
		apmIpv6LeasepoolStatMaxAssigned,
		apmIpv6LeasepoolStatTotPickRequests,
		apmIpv6LeasepoolStatTotPickFailure,
		apmIpv6LeasepoolStatTotReserveRequests,
		apmIpv6LeasepoolStatTotReserveFailure,
		apmIpv6LeasepoolStatTotReleaseRequests,
		apmIpv6LeasepoolStatTotReleaseFailure
	}
	STATUS	 current
	DESCRIPTION
		"A collection of objects of apmIpv6LeasepoolStat MIB."
	::= { bigipApmGroups 12 }
END
